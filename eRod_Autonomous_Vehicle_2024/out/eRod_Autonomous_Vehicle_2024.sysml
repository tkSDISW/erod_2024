package  'eRod_Autonomous_Vehicle_2024 Project' {
    import ARCADIA::**; 
    @PackageMeta {
        type = "Project";
    } 
    @CapellaID { eid = "dbe4faa0-fc02-49e0-93a2-a3d664caadf8"; } 
    enum def 'ProgressStatus' :> EnumerationPropertyType  { 
        enum 'DRAFT'; 
        enum 'TO_BE_REVIEWED'; 
        enum 'TO_BE_DISCUSSED'; 
        enum 'REWORK_NECESSARY'; 
        enum 'UNDER_REWORK'; 
        enum 'REVIEWED_OK'; 
    }  
    package  'eRod_Autonomous_Vehicle_2024' {
        @PackageMeta {
            type = "SystemEngineering";
        } 
        doc /*
        <p><img src="eRod_Autonomous_Vehicle_2024/images/20230907_082833_267224.png" /></p>

        */ 
        @CapellaID { eid = "94049337-dbca-4978-aac1-028d958e11f6"; } 
        package  'SMW Properties' {
            @PackageMeta {
                type = "PropertyValuePkg";
            } 
            @CapellaID { eid = "d3429ba2-94ab-4c9c-817e-b5e361743202"; } 
            package  'Parameters' {
                @PackageMeta {
                    type = "PropertyValuePkg";
                } 
                @CapellaID { eid = "14bed385-f4c9-4674-ae68-d040f9ca0770"; } 
                attribute 'Right Steering Knuckle Mass' : PropertyValueGroup { 
                    @CapellaID { eid = "cd165f70-61e1-41e7-a172-1dab211f6d45"; } 
                    attribute :>> summary = ""; 
                    attribute 'Goal' : FloatPropertyValue  = 1.8 { 
                        @CapellaID { eid = "7678aee8-26ed-43a7-83e3-edecb9b0ce60"; } 
                    }  
                    attribute 'Min' : FloatPropertyValue  = 1.0 { 
                        @CapellaID { eid = "13157616-362a-49d8-a570-51e4f098b557"; } 
                    }  
                    attribute 'Max' : FloatPropertyValue  = 3.0 { 
                        @CapellaID { eid = "2eb51e68-1ba2-481a-938e-b3cc8014a75a"; } 
                    }  
                    ref :>> ownedPropertyValues =  ('eRod_Autonomous_Vehicle_2024 Project'::'eRod_Autonomous_Vehicle_2024'::'SMW Properties'::'Parameters'::'Right Steering Knuckle Mass'.'Goal',
                    'eRod_Autonomous_Vehicle_2024 Project'::'eRod_Autonomous_Vehicle_2024'::'SMW Properties'::'Parameters'::'Right Steering Knuckle Mass'.'Min',
                    'eRod_Autonomous_Vehicle_2024 Project'::'eRod_Autonomous_Vehicle_2024'::'SMW Properties'::'Parameters'::'Right Steering Knuckle Mass'.'Max'); 
                     
                }  
                attribute 'Mass Range' : PropertyValueGroup { 
                    @CapellaID { eid = "ac7812b0-d2d1-45f8-bd32-abe0c405ad33"; } 
                    attribute :>> summary = ""; 
                    attribute 'Goal' : FloatPropertyValue  = 6.25 { 
                        @CapellaID { eid = "f4d62dc3-71dc-43af-8410-52242e0cbc8b"; } 
                    }  
                    attribute 'Min' : FloatPropertyValue  = 6.0 { 
                        @CapellaID { eid = "fcf66047-b7d3-4fd2-b26f-b23a2da85065"; } 
                    }  
                    attribute 'Max' : FloatPropertyValue  = 6.5 { 
                        @CapellaID { eid = "9497a7de-29ba-4a3d-a7bc-5874dbb40688"; } 
                    }  
                    ref :>> ownedPropertyValues =  ('eRod_Autonomous_Vehicle_2024 Project'::'eRod_Autonomous_Vehicle_2024'::'SMW Properties'::'Parameters'::'Mass Range'.'Goal',
                    'eRod_Autonomous_Vehicle_2024 Project'::'eRod_Autonomous_Vehicle_2024'::'SMW Properties'::'Parameters'::'Mass Range'.'Min',
                    'eRod_Autonomous_Vehicle_2024 Project'::'eRod_Autonomous_Vehicle_2024'::'SMW Properties'::'Parameters'::'Mass Range'.'Max'); 
                     
                }  
            } 
            enum def 'SMW_REMOTE_OBJ_KIND' :> EnumerationPropertyType  { 
                enum 'ParamDbl'; 
            }  
            enum def 'SMW_SYNC_STATUS' :> EnumerationPropertyType  { 
                enum 'SYNC'; 
                enum 'SYNC_DEEP'; 
            }  
        } 
        package  'Operational Analysis' {
            @PackageMeta {
                type = "OperationalAnalysis";
            } 
            @CapellaID { eid = "fe39d0b9-d0b5-4d1f-90f1-df0c554e7c28"; } 
            package  'Operational Activities' {
                @PackageMeta {
                    type = "OperationalActivityPkg";
                } 
                @CapellaID { eid = "4f71a708-7c2f-4af7-aae3-c1332d8c50ca"; } 
                action 'Root Operational Activity' : OperationalActivity  { 
                    @CapellaID { eid = "43d627dd-0123-4898-9b1f-43236b41c5f6"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> kind = FunctionKind::FUNCTION; 
                    attribute :>> isMaxInclusive = false; 
                    attribute :>> isMinInclusive = false; 
                    attribute :>> isOrdered = false; 
                    attribute :>> isUnique = false; 
                    action 'Car racing' : OperationalProcess  { 
                        @CapellaID { eid = "28bc1b6b-251b-4187-a516-8554acadd969"; } 
                        attribute :>> kind = FunctionalChainKind::SIMPLE; 
                        ref action '4132f153-42a4-4797-b60e-06e1211e21eb' = 'eRod_Autonomous_Vehicle_2024 Project'::'eRod_Autonomous_Vehicle_2024'::'Operational Analysis'::'Operational Activities'::'Root Operational Activity'.'Drive on a race track'; 
                        connection 'c7c2b35b-52b0-4fc8-ae39-319c4a73da48' : FunctionalChainInvolvementLink 
                            connect source ::> 'eRod_Autonomous_Vehicle_2024 Project'::'eRod_Autonomous_Vehicle_2024'::'Operational Analysis'::'Operational Activities'::'Root Operational Activity'.'Car racing'.'4132f153-42a4-4797-b60e-06e1211e21eb'
                            to  target ::> 'eRod_Autonomous_Vehicle_2024 Project'::'eRod_Autonomous_Vehicle_2024'::'Operational Analysis'::'Operational Activities'::'Root Operational Activity'.'Car racing'.'bcc54a3e-9abd-462e-b38b-f8ab2a910ed0' {

                                ref :>> involved = 'eRod_Autonomous_Vehicle_2024 Project'::'eRod_Autonomous_Vehicle_2024'::'Operational Analysis'::'Operational Activities'::'Root Operational Activity'.'977b5caa-70f3-4c7e-b032-362c17973ba4';

                            } 
                        ref action 'bcc54a3e-9abd-462e-b38b-f8ab2a910ed0' = 'eRod_Autonomous_Vehicle_2024 Project'::'eRod_Autonomous_Vehicle_2024'::'Operational Analysis'::'Operational Activities'::'Root Operational Activity'.'Sporty drive'; 
                        connection '229225a4-327a-4cde-9d5f-bc0febff2bcf' : FunctionalChainInvolvementLink 
                            connect source ::> 'eRod_Autonomous_Vehicle_2024 Project'::'eRod_Autonomous_Vehicle_2024'::'Operational Analysis'::'Operational Activities'::'Root Operational Activity'.'Car racing'.'bcc54a3e-9abd-462e-b38b-f8ab2a910ed0'
                            to  target ::> 'eRod_Autonomous_Vehicle_2024 Project'::'eRod_Autonomous_Vehicle_2024'::'Operational Analysis'::'Operational Activities'::'Root Operational Activity'.'Car racing'.'5bfc4d49-0586-4aa9-b18c-3d5929fd0637' {

                                ref :>> involved = 'eRod_Autonomous_Vehicle_2024 Project'::'eRod_Autonomous_Vehicle_2024'::'Operational Analysis'::'Operational Activities'::'Root Operational Activity'.'4e7d42f3-4119-417c-9f11-95b7198c264e';

                            } 
                        ref action '5bfc4d49-0586-4aa9-b18c-3d5929fd0637' = 'eRod_Autonomous_Vehicle_2024 Project'::'eRod_Autonomous_Vehicle_2024'::'Operational Analysis'::'Operational Activities'::'Root Operational Activity'.'Car racing experience'; 
                    }  
                    action 'Remote update' : OperationalProcess  { 
                        @CapellaID { eid = "a71c2618-a479-45b3-b67f-207b62abee65"; } 
                        attribute :>> kind = FunctionalChainKind::SIMPLE; 
                        ref action 'a9519684-f020-4f0b-80bd-696dd0038863' = 'eRod_Autonomous_Vehicle_2024 Project'::'eRod_Autonomous_Vehicle_2024'::'Operational Analysis'::'Operational Activities'::'Root Operational Activity'.'Motor overheating warning '; 
                        connection 'a389e0f3-3ce1-44b7-a5b1-2e76a61626db' : FunctionalChainInvolvementLink 
                            connect source ::> 'eRod_Autonomous_Vehicle_2024 Project'::'eRod_Autonomous_Vehicle_2024'::'Operational Analysis'::'Operational Activities'::'Root Operational Activity'.'Remote update'.'a9519684-f020-4f0b-80bd-696dd0038863'
                            to  target ::> 'eRod_Autonomous_Vehicle_2024 Project'::'eRod_Autonomous_Vehicle_2024'::'Operational Analysis'::'Operational Activities'::'Root Operational Activity'.'Remote update'.'53775da3-77e5-4937-8456-eb3dff13b97b' {

                                ref :>> involved = 'eRod_Autonomous_Vehicle_2024 Project'::'eRod_Autonomous_Vehicle_2024'::'Operational Analysis'::'Operational Activities'::'Root Operational Activity'.'2cdb4cf1-a4d0-437e-b342-cc6a9c1fb973';

                            } 
                        ref action '53775da3-77e5-4937-8456-eb3dff13b97b' = 'eRod_Autonomous_Vehicle_2024 Project'::'eRod_Autonomous_Vehicle_2024'::'Operational Analysis'::'Operational Activities'::'Root Operational Activity'.'Report issues'; 
                        connection '2672cbac-f257-4a77-8325-504b15087dca' : FunctionalChainInvolvementLink 
                            connect source ::> 'eRod_Autonomous_Vehicle_2024 Project'::'eRod_Autonomous_Vehicle_2024'::'Operational Analysis'::'Operational Activities'::'Root Operational Activity'.'Remote update'.'53775da3-77e5-4937-8456-eb3dff13b97b'
                            to  target ::> 'eRod_Autonomous_Vehicle_2024 Project'::'eRod_Autonomous_Vehicle_2024'::'Operational Analysis'::'Operational Activities'::'Root Operational Activity'.'Remote update'.'cffec057-0725-409c-85b8-eb2048c8a863' {

                                ref :>> involved = 'eRod_Autonomous_Vehicle_2024 Project'::'eRod_Autonomous_Vehicle_2024'::'Operational Analysis'::'Operational Activities'::'Root Operational Activity'.'5a3af137-b554-411d-8d51-a26b3d748bf2';

                            } 
                        ref action 'cffec057-0725-409c-85b8-eb2048c8a863' = 'eRod_Autonomous_Vehicle_2024 Project'::'eRod_Autonomous_Vehicle_2024'::'Operational Analysis'::'Operational Activities'::'Root Operational Activity'.'Recieve issue'; 
                        connection 'c588f53a-7c9d-4d28-bfc8-4aa21b78b8f8' : FunctionalChainInvolvementLink 
                            connect source ::> 'eRod_Autonomous_Vehicle_2024 Project'::'eRod_Autonomous_Vehicle_2024'::'Operational Analysis'::'Operational Activities'::'Root Operational Activity'.'Remote update'.'cffec057-0725-409c-85b8-eb2048c8a863'
                            to  target ::> 'eRod_Autonomous_Vehicle_2024 Project'::'eRod_Autonomous_Vehicle_2024'::'Operational Analysis'::'Operational Activities'::'Root Operational Activity'.'Remote update'.'1ab11454-4cd8-4d51-8c11-126a77e4f9da' {

                                ref :>> involved = 'eRod_Autonomous_Vehicle_2024 Project'::'eRod_Autonomous_Vehicle_2024'::'Operational Analysis'::'Operational Activities'::'Root Operational Activity'.'294cccd3-0efa-4370-b7f9-dbb6892bc5c6';

                            } 
                        ref action '1ab11454-4cd8-4d51-8c11-126a77e4f9da' = 'eRod_Autonomous_Vehicle_2024 Project'::'eRod_Autonomous_Vehicle_2024'::'Operational Analysis'::'Operational Activities'::'Root Operational Activity'.'Provide solution'; 
                        connection 'c4a4cef6-a798-4280-a9f9-b199e22cb9c2' : FunctionalChainInvolvementLink 
                            connect source ::> 'eRod_Autonomous_Vehicle_2024 Project'::'eRod_Autonomous_Vehicle_2024'::'Operational Analysis'::'Operational Activities'::'Root Operational Activity'.'Remote update'.'1ab11454-4cd8-4d51-8c11-126a77e4f9da'
                            to  target ::> 'eRod_Autonomous_Vehicle_2024 Project'::'eRod_Autonomous_Vehicle_2024'::'Operational Analysis'::'Operational Activities'::'Root Operational Activity'.'Remote update'.'badd05e4-d961-44d4-bc48-84ef9d335f63' {

                                ref :>> involved = 'eRod_Autonomous_Vehicle_2024 Project'::'eRod_Autonomous_Vehicle_2024'::'Operational Analysis'::'Operational Activities'::'Root Operational Activity'.'7e9ba078-437e-424e-a31b-379003b8d438';

                            } 
                        ref action 'badd05e4-d961-44d4-bc48-84ef9d335f63' = 'eRod_Autonomous_Vehicle_2024 Project'::'eRod_Autonomous_Vehicle_2024'::'Operational Analysis'::'Operational Activities'::'Root Operational Activity'.'Informed Software update'; 
                        connection '09976fa6-0e49-4896-bc02-ec415022cc82' : FunctionalChainInvolvementLink 
                            connect source ::> 'eRod_Autonomous_Vehicle_2024 Project'::'eRod_Autonomous_Vehicle_2024'::'Operational Analysis'::'Operational Activities'::'Root Operational Activity'.'Remote update'.'badd05e4-d961-44d4-bc48-84ef9d335f63'
                            to  target ::> 'eRod_Autonomous_Vehicle_2024 Project'::'eRod_Autonomous_Vehicle_2024'::'Operational Analysis'::'Operational Activities'::'Root Operational Activity'.'Remote update'.'cfaf7731-fda2-4aa2-a21b-9579f93aff94' {

                                ref :>> involved = 'eRod_Autonomous_Vehicle_2024 Project'::'eRod_Autonomous_Vehicle_2024'::'Operational Analysis'::'Operational Activities'::'Root Operational Activity'.'5ac50b2c-b8c1-4f04-85ad-51b192d3012c';

                            } 
                        ref action 'cfaf7731-fda2-4aa2-a21b-9579f93aff94' = 'eRod_Autonomous_Vehicle_2024 Project'::'eRod_Autonomous_Vehicle_2024'::'Operational Analysis'::'Operational Activities'::'Root Operational Activity'.'Get software update'; 
                        connection '76c8411e-2e82-466f-91cc-5508909e8ab2' : FunctionalChainInvolvementLink 
                            connect source ::> 'eRod_Autonomous_Vehicle_2024 Project'::'eRod_Autonomous_Vehicle_2024'::'Operational Analysis'::'Operational Activities'::'Root Operational Activity'.'Remote update'.'cfaf7731-fda2-4aa2-a21b-9579f93aff94'
                            to  target ::> 'eRod_Autonomous_Vehicle_2024 Project'::'eRod_Autonomous_Vehicle_2024'::'Operational Analysis'::'Operational Activities'::'Root Operational Activity'.'Remote update'.'c7bc657e-f717-45e7-8c27-3d5be77b782a' {

                                ref :>> involved = 'eRod_Autonomous_Vehicle_2024 Project'::'eRod_Autonomous_Vehicle_2024'::'Operational Analysis'::'Operational Activities'::'Root Operational Activity'.'e411a798-a889-4f53-9ec7-a427dbc97796';

                            } 
                        ref action 'c7bc657e-f717-45e7-8c27-3d5be77b782a' = 'eRod_Autonomous_Vehicle_2024 Project'::'eRod_Autonomous_Vehicle_2024'::'Operational Analysis'::'Operational Activities'::'Root Operational Activity'.'Sporty drive'; 
                    }  
                    action 'Activate Autonmous' : OperationalProcess  { 
                        @CapellaID { eid = "fbb5754e-07df-4bd2-9716-4d668be9dec6"; } 
                        attribute :>> kind = FunctionalChainKind::SIMPLE; 
                        connection 'af6e8b30-dc7e-470d-80e7-2e760f8839e1' : FunctionalChainInvolvementLink 
                            connect source ::> 'eRod_Autonomous_Vehicle_2024 Project'::'eRod_Autonomous_Vehicle_2024'::'Operational Analysis'::'Operational Activities'::'Root Operational Activity'.'Activate Autonmous'.'acb191be-c796-41c4-b386-cd6611c0ca43'
                            to  target ::> 'eRod_Autonomous_Vehicle_2024 Project'::'eRod_Autonomous_Vehicle_2024'::'Operational Analysis'::'Operational Activities'::'Root Operational Activity'.'Activate Autonmous'.'b7d76ab4-61b4-4bd0-a262-06723f41eb80' {

                                ref :>> involved = 'eRod_Autonomous_Vehicle_2024 Project'::'eRod_Autonomous_Vehicle_2024'::'Operational Analysis'::'Operational Activities'::'Root Operational Activity'.'20bcc67f-ebd7-4369-a9c7-ff780c6f7238';

                            } 
                        ref action 'b7d76ab4-61b4-4bd0-a262-06723f41eb80' = 'eRod_Autonomous_Vehicle_2024 Project'::'eRod_Autonomous_Vehicle_2024'::'Operational Analysis'::'Operational Activities'::'Root Operational Activity'.'Autonomous Driving'; 
                        ref action 'acb191be-c796-41c4-b386-cd6611c0ca43' = 'eRod_Autonomous_Vehicle_2024 Project'::'eRod_Autonomous_Vehicle_2024'::'Operational Analysis'::'Operational Activities'::'Root Operational Activity'.'Drive vehicle'; 
                    }  
                    action 'Resume Driver Control' : OperationalProcess  { 
                        @CapellaID { eid = "a65fafab-6c2c-4f51-8070-36824cc33d0b"; } 
                        attribute :>> kind = FunctionalChainKind::SIMPLE; 
                        connection '87860441-606a-475a-904a-880533a3d109' : FunctionalChainInvolvementLink 
                            connect source ::> 'eRod_Autonomous_Vehicle_2024 Project'::'eRod_Autonomous_Vehicle_2024'::'Operational Analysis'::'Operational Activities'::'Root Operational Activity'.'Resume Driver Control'.'6a4f3d41-53e3-4e8f-b836-0cfc5c42c902'
                            to  target ::> 'eRod_Autonomous_Vehicle_2024 Project'::'eRod_Autonomous_Vehicle_2024'::'Operational Analysis'::'Operational Activities'::'Root Operational Activity'.'Resume Driver Control'.'98a46777-d182-4f78-be12-94d92f487bb7' {

                                ref :>> involved = 'eRod_Autonomous_Vehicle_2024 Project'::'eRod_Autonomous_Vehicle_2024'::'Operational Analysis'::'Operational Activities'::'Root Operational Activity'.'287325bf-5771-47e4-a180-0e2bf3a565a4';

                            } 
                        ref action '98a46777-d182-4f78-be12-94d92f487bb7' = 'eRod_Autonomous_Vehicle_2024 Project'::'eRod_Autonomous_Vehicle_2024'::'Operational Analysis'::'Operational Activities'::'Root Operational Activity'.'Drive vehicle'; 
                        ref action '6a4f3d41-53e3-4e8f-b836-0cfc5c42c902' = 'eRod_Autonomous_Vehicle_2024 Project'::'eRod_Autonomous_Vehicle_2024'::'Operational Analysis'::'Operational Activities'::'Root Operational Activity'.'Autonomous Driving'; 
                    }  
                    action 'Remote Park' : OperationalProcess  { 
                        @CapellaID { eid = "9284833e-b4bd-4c15-bc18-ef3337339a7f"; } 
                        attribute :>> kind = FunctionalChainKind::SIMPLE; 
                        connection '618690c9-c0ec-47ae-adec-9887917d8ab3' : FunctionalChainInvolvementLink 
                            connect source ::> 'eRod_Autonomous_Vehicle_2024 Project'::'eRod_Autonomous_Vehicle_2024'::'Operational Analysis'::'Operational Activities'::'Root Operational Activity'.'Remote Park'.'4b2d3da1-28fc-4377-aa6a-b2c65b4d9daf'
                            to  target ::> 'eRod_Autonomous_Vehicle_2024 Project'::'eRod_Autonomous_Vehicle_2024'::'Operational Analysis'::'Operational Activities'::'Root Operational Activity'.'Remote Park'.'4d820165-6ee2-461a-a97d-9df92758e2b0' {

                                ref :>> involved = 'eRod_Autonomous_Vehicle_2024 Project'::'eRod_Autonomous_Vehicle_2024'::'Operational Analysis'::'Operational Activities'::'Root Operational Activity'.'5a01edc2-42f9-40d5-a818-b5f0a5216281';

                            } 
                        ref action '4d820165-6ee2-461a-a97d-9df92758e2b0' = 'eRod_Autonomous_Vehicle_2024 Project'::'eRod_Autonomous_Vehicle_2024'::'Operational Analysis'::'Operational Activities'::'Root Operational Activity'.'Remote Operate Car'; 
                        ref action '4b2d3da1-28fc-4377-aa6a-b2c65b4d9daf' = 'eRod_Autonomous_Vehicle_2024 Project'::'eRod_Autonomous_Vehicle_2024'::'Operational Analysis'::'Operational Activities'::'Root Operational Activity'.'Vehicle Command'; 
                        connection '5b894234-499d-4d0a-95df-0cf3ad579dd1' : FunctionalChainInvolvementLink 
                            connect source ::> 'eRod_Autonomous_Vehicle_2024 Project'::'eRod_Autonomous_Vehicle_2024'::'Operational Analysis'::'Operational Activities'::'Root Operational Activity'.'Remote Park'.'4d820165-6ee2-461a-a97d-9df92758e2b0'
                            to  target ::> 'eRod_Autonomous_Vehicle_2024 Project'::'eRod_Autonomous_Vehicle_2024'::'Operational Analysis'::'Operational Activities'::'Root Operational Activity'.'Remote Park'.'25675e70-46e0-49d8-a886-522b6145bc12' {

                                ref :>> involved = 'eRod_Autonomous_Vehicle_2024 Project'::'eRod_Autonomous_Vehicle_2024'::'Operational Analysis'::'Operational Activities'::'Root Operational Activity'.'3ab8c3d1-97d1-427d-b38b-8e979a3a3bde';

                            } 
                        ref action '25675e70-46e0-49d8-a886-522b6145bc12' = 'eRod_Autonomous_Vehicle_2024 Project'::'eRod_Autonomous_Vehicle_2024'::'Operational Analysis'::'Operational Activities'::'Root Operational Activity'.'Park vehicle'; 
                        connection '4b5b7018-547d-4574-81b3-a1463767f4bd' : FunctionalChainInvolvementLink 
                            connect source ::> 'eRod_Autonomous_Vehicle_2024 Project'::'eRod_Autonomous_Vehicle_2024'::'Operational Analysis'::'Operational Activities'::'Root Operational Activity'.'Remote Park'.'25675e70-46e0-49d8-a886-522b6145bc12'
                            to  target ::> 'eRod_Autonomous_Vehicle_2024 Project'::'eRod_Autonomous_Vehicle_2024'::'Operational Analysis'::'Operational Activities'::'Root Operational Activity'.'Remote Park'.'62404d24-a9ad-46b9-8256-00d8e49e4208' {

                                ref :>> involved = 'eRod_Autonomous_Vehicle_2024 Project'::'eRod_Autonomous_Vehicle_2024'::'Operational Analysis'::'Operational Activities'::'Root Operational Activity'.'8851dc30-4395-4b6c-b893-e49544d23f59';

                            } 
                        ref action '62404d24-a9ad-46b9-8256-00d8e49e4208' = 'eRod_Autonomous_Vehicle_2024 Project'::'eRod_Autonomous_Vehicle_2024'::'Operational Analysis'::'Operational Activities'::'Root Operational Activity'.'Control braking'; 
                        connection '42b24bb9-5bf7-415d-ad20-974336bf36aa' : FunctionalChainInvolvementLink 
                            connect source ::> 'eRod_Autonomous_Vehicle_2024 Project'::'eRod_Autonomous_Vehicle_2024'::'Operational Analysis'::'Operational Activities'::'Root Operational Activity'.'Remote Park'.'25675e70-46e0-49d8-a886-522b6145bc12'
                            to  target ::> 'eRod_Autonomous_Vehicle_2024 Project'::'eRod_Autonomous_Vehicle_2024'::'Operational Analysis'::'Operational Activities'::'Root Operational Activity'.'Remote Park'.'7b33ec55-88ca-4e2f-a9b5-f1b353bc5d7d' {

                                ref :>> involved = 'eRod_Autonomous_Vehicle_2024 Project'::'eRod_Autonomous_Vehicle_2024'::'Operational Analysis'::'Operational Activities'::'Root Operational Activity'.'6d432554-477c-4241-9a53-cd3c72fd0126';

                            } 
                        ref action '7b33ec55-88ca-4e2f-a9b5-f1b353bc5d7d' = 'eRod_Autonomous_Vehicle_2024 Project'::'eRod_Autonomous_Vehicle_2024'::'Operational Analysis'::'Operational Activities'::'Root Operational Activity'.'Steer Wheels'; 
                        connection 'ea4960ca-1313-4f7d-b547-8d68ce6383c0' : FunctionalChainInvolvementLink 
                            connect source ::> 'eRod_Autonomous_Vehicle_2024 Project'::'eRod_Autonomous_Vehicle_2024'::'Operational Analysis'::'Operational Activities'::'Root Operational Activity'.'Remote Park'.'7b33ec55-88ca-4e2f-a9b5-f1b353bc5d7d'
                            to  target ::> 'eRod_Autonomous_Vehicle_2024 Project'::'eRod_Autonomous_Vehicle_2024'::'Operational Analysis'::'Operational Activities'::'Root Operational Activity'.'Remote Park'.'fdd24f91-a33f-4669-aea3-91c1183f5c75' {

                                ref :>> involved = 'eRod_Autonomous_Vehicle_2024 Project'::'eRod_Autonomous_Vehicle_2024'::'Operational Analysis'::'Operational Activities'::'Root Operational Activity'.'28ee1538-7d17-4a8f-b43c-6c67de0ef9a0';

                            } 
                        ref action 'fdd24f91-a33f-4669-aea3-91c1183f5c75' = 'eRod_Autonomous_Vehicle_2024 Project'::'eRod_Autonomous_Vehicle_2024'::'Operational Analysis'::'Operational Activities'::'Root Operational Activity'.'Deliver traction to surface'; 
                        connection 'f779951f-b60c-4cfd-a825-0db1935e4653' : FunctionalChainInvolvementLink 
                            connect source ::> 'eRod_Autonomous_Vehicle_2024 Project'::'eRod_Autonomous_Vehicle_2024'::'Operational Analysis'::'Operational Activities'::'Root Operational Activity'.'Remote Park'.'fdd24f91-a33f-4669-aea3-91c1183f5c75'
                            to  target ::> 'eRod_Autonomous_Vehicle_2024 Project'::'eRod_Autonomous_Vehicle_2024'::'Operational Analysis'::'Operational Activities'::'Root Operational Activity'.'Remote Park'.'f7e930de-696e-4087-ba82-8bfc69768fa2' {

                                ref :>> involved = 'eRod_Autonomous_Vehicle_2024 Project'::'eRod_Autonomous_Vehicle_2024'::'Operational Analysis'::'Operational Activities'::'Root Operational Activity'.'5bb84516-7881-44ea-8b6b-97e9b2816b1b';

                            } 
                        ref action 'f7e930de-696e-4087-ba82-8bfc69768fa2' = 'eRod_Autonomous_Vehicle_2024 Project'::'eRod_Autonomous_Vehicle_2024'::'Operational Analysis'::'Operational Activities'::'Root Operational Activity'.'Provide diverse terrain'; 
                        ref action '2f73e1e2-c7d2-49c4-8380-c54a38efce32' = 'eRod_Autonomous_Vehicle_2024 Project'::'eRod_Autonomous_Vehicle_2024'::'Operational Analysis'::'Operational Activities'::'Root Operational Activity'.'Status and command indication'; 
                        connection 'c15ae7eb-422f-4a18-8c12-406da5e53de2' : FunctionalChainInvolvementLink 
                            connect source ::> 'eRod_Autonomous_Vehicle_2024 Project'::'eRod_Autonomous_Vehicle_2024'::'Operational Analysis'::'Operational Activities'::'Root Operational Activity'.'Remote Park'.'2f73e1e2-c7d2-49c4-8380-c54a38efce32'
                            to  target ::> 'eRod_Autonomous_Vehicle_2024 Project'::'eRod_Autonomous_Vehicle_2024'::'Operational Analysis'::'Operational Activities'::'Root Operational Activity'.'Remote Park'.'25675e70-46e0-49d8-a886-522b6145bc12' {

                                ref :>> involved = 'eRod_Autonomous_Vehicle_2024 Project'::'eRod_Autonomous_Vehicle_2024'::'Operational Analysis'::'Operational Activities'::'Root Operational Activity'.'cd03edc3-cf39-42eb-a3dc-4d00c66e61b7';

                            } 
                        ref action '82a776b9-8686-430a-87cb-7fab246958b9' = 'eRod_Autonomous_Vehicle_2024 Project'::'eRod_Autonomous_Vehicle_2024'::'Operational Analysis'::'Operational Activities'::'Root Operational Activity'.'Receive Status of Progess '; 
                        connection '84ddb689-55d1-4ed3-93d3-aeefd766a731' : FunctionalChainInvolvementLink 
                            connect source ::> 'eRod_Autonomous_Vehicle_2024 Project'::'eRod_Autonomous_Vehicle_2024'::'Operational Analysis'::'Operational Activities'::'Root Operational Activity'.'Remote Park'.'2f73e1e2-c7d2-49c4-8380-c54a38efce32'
                            to  target ::> 'eRod_Autonomous_Vehicle_2024 Project'::'eRod_Autonomous_Vehicle_2024'::'Operational Analysis'::'Operational Activities'::'Root Operational Activity'.'Remote Park'.'82a776b9-8686-430a-87cb-7fab246958b9' {

                                ref :>> involved = 'eRod_Autonomous_Vehicle_2024 Project'::'eRod_Autonomous_Vehicle_2024'::'Operational Analysis'::'Operational Activities'::'Root Operational Activity'.'3d30dfea-cc32-414e-9e96-fe69a71ce318';

                            } 
                    }  
                    action 'Drive on a race track' : OperationalActivity  { 
                        @CapellaID { eid = "2afe42d7-aecd-4433-a908-a28c610661ff"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Sporty drive' : OperationalActivity  { 
                        @CapellaID { eid = "f0edb149-2187-497b-a5d2-779d29e3343a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Car racing experience' : OperationalActivity  { 
                        @CapellaID { eid = "a730d5fe-1f4b-408d-91b6-a2c013c6230d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Motor overheating warning ' : OperationalActivity  { 
                        @CapellaID { eid = "a40b4af7-50d3-4691-a8b0-69ed35ffb76e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Get software update' : OperationalActivity  { 
                        @CapellaID { eid = "800d8225-981d-42a0-b560-7f0d9ced4c23"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Report issues' : OperationalActivity  { 
                        @CapellaID { eid = "727fc06e-436e-4f6f-89b4-a1eb5c2ca782"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Recieve issue' : OperationalActivity  { 
                        @CapellaID { eid = "309e9171-c152-45d8-833e-8fa83ddb7009"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Provide solution' : OperationalActivity  { 
                        @CapellaID { eid = "96f73fbe-40af-4f25-b90f-12d3507aa824"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Informed Software update' : OperationalActivity  { 
                        @CapellaID { eid = "33ce90a8-019a-4522-baa3-53eee9500705"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Drive vehicle' : OperationalActivity  { 
                        @CapellaID { eid = "4a482311-9717-4ce5-87c2-a4707891fe36"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Autonomous Driving' : OperationalActivity  { 
                        @CapellaID { eid = "2d58cbc0-7fd5-40bb-9500-63212e2288c0"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Provide diverse terrain' : OperationalActivity  { 
                        @CapellaID { eid = "210d2c2a-4d94-49c3-ba8e-c25dffd06fc4"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Provide parking location' : OperationalActivity  { 
                        @CapellaID { eid = "e330657c-c2ef-46d7-895c-bce9c5d43afe"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Provide weather' : OperationalActivity  { 
                        @CapellaID { eid = "fd8706e5-f77c-4c2d-a6af-cc9af0767450"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Provide Object Locations' : OperationalActivity  { 
                        @CapellaID { eid = "3d42517d-8589-4739-bd88-3cb7ab240051"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Provide electricity' : OperationalActivity  { 
                        @CapellaID { eid = "6510e834-c784-44bc-b787-37b5a973e9a1"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Store energy' : OperationalActivity  { 
                        @CapellaID { eid = "75c7881f-e7a5-459b-98d0-7d29c565a3fc"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Connect charger' : OperationalActivity  { 
                        @CapellaID { eid = "eb1124a3-eda3-4301-8734-ccc1b1700582"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Activate Park Assist' : OperationalActivity  { 
                        @CapellaID { eid = "9eddca3f-10e0-4aa8-93da-caf5199da751"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Status and command indication' : OperationalActivity  { 
                        @CapellaID { eid = "df3371aa-9476-46dd-bbd5-bd14ac4a8a17"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Park vehicle' : OperationalActivity  { 
                        @CapellaID { eid = "c6232ac0-0df9-4d41-8601-f50cff2054d3"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Avoid collision' : OperationalActivity  { 
                        @CapellaID { eid = "9a2e892f-4af5-40de-be46-5cfc69bd7823"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Control braking' : OperationalActivity  { 
                        @CapellaID { eid = "09bfb754-d97e-4f94-abeb-bb17f46e8fcb"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Provide vehicle status' : OperationalActivity  { 
                        @CapellaID { eid = "e8aa6775-19bc-4df3-95fb-de4cd590036a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Observe status' : OperationalActivity  { 
                        @CapellaID { eid = "a01e3d3f-7a4e-4d81-826b-dadba1995e3f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Locate targets' : OperationalActivity  { 
                        @CapellaID { eid = "1d6af9fd-c76f-4707-ac87-d29598c4ffba"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Deliver traction to surface' : OperationalActivity  { 
                        @CapellaID { eid = "b38cdb77-cba4-40d8-8999-a087eb232b7c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Maintain distance' : OperationalActivity  { 
                        @CapellaID { eid = "90bedec0-db46-4ff6-b758-b7d54e8c9a84"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Vehicle Command' : OperationalActivity  { 
                        @CapellaID { eid = "2dc54b50-475e-48de-b9fe-2b7c8928258d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Remote Operate Car' : OperationalActivity  { 
                        @CapellaID { eid = "314af37d-431a-4653-8244-33d2fed01d23"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Steer Wheels' : OperationalActivity  { 
                        @CapellaID { eid = "378edc5c-3d19-4a47-ab2e-3b7136d28d4d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Receive Status of Progess ' : OperationalActivity  { 
                        @CapellaID { eid = "ed5d414e-989e-450a-afca-0d02d470ae97"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    connection '977b5caa-70f3-4c7e-b032-362c17973ba4' : OAInteraction 
                        connect source ::> 'eRod_Autonomous_Vehicle_2024 Project'::'eRod_Autonomous_Vehicle_2024'::'Operational Analysis'::'Operational Activities'::'Root Operational Activity'.'Drive on a race track'
                        to  target ::> 'eRod_Autonomous_Vehicle_2024 Project'::'eRod_Autonomous_Vehicle_2024'::'Operational Analysis'::'Operational Activities'::'Root Operational Activity'.'Sporty drive' { 
                        @CapellaID { eid = "977b5caa-70f3-4c7e-b032-362c17973ba4"; } 
                        attribute :>> isMulticast = false; 
                        attribute :>> isMultireceive = false; 
                        attribute :>> kindOfRate = RateKind::Unspecified; 
                        attribute :>> interfaceName = "Command"; 
                    }  
                    connection '4e7d42f3-4119-417c-9f11-95b7198c264e' : OAInteraction 
                        connect source ::> 'eRod_Autonomous_Vehicle_2024 Project'::'eRod_Autonomous_Vehicle_2024'::'Operational Analysis'::'Operational Activities'::'Root Operational Activity'.'Sporty drive'
                        to  target ::> 'eRod_Autonomous_Vehicle_2024 Project'::'eRod_Autonomous_Vehicle_2024'::'Operational Analysis'::'Operational Activities'::'Root Operational Activity'.'Car racing experience' { 
                        @CapellaID { eid = "4e7d42f3-4119-417c-9f11-95b7198c264e"; } 
                        attribute :>> isMulticast = false; 
                        attribute :>> isMultireceive = false; 
                        attribute :>> kindOfRate = RateKind::Unspecified; 
                        attribute :>> interfaceName = "Provide"; 
                    }  
                    connection '48b9100c-c194-4d69-9a4e-13fd46674196' : OAInteraction 
                        connect source ::> 'eRod_Autonomous_Vehicle_2024 Project'::'eRod_Autonomous_Vehicle_2024'::'Operational Analysis'::'Operational Activities'::'Root Operational Activity'.'Sporty drive'
                        to  target ::> 'eRod_Autonomous_Vehicle_2024 Project'::'eRod_Autonomous_Vehicle_2024'::'Operational Analysis'::'Operational Activities'::'Root Operational Activity'.'Motor overheating warning ' { 
                        @CapellaID { eid = "48b9100c-c194-4d69-9a4e-13fd46674196"; } 
                        attribute :>> isMulticast = false; 
                        attribute :>> isMultireceive = false; 
                        attribute :>> kindOfRate = RateKind::Unspecified; 
                        attribute :>> interfaceName = "Cause"; 
                    }  
                    connection '2cdb4cf1-a4d0-437e-b342-cc6a9c1fb973' : OAInteraction 
                        connect source ::> 'eRod_Autonomous_Vehicle_2024 Project'::'eRod_Autonomous_Vehicle_2024'::'Operational Analysis'::'Operational Activities'::'Root Operational Activity'.'Motor overheating warning '
                        to  target ::> 'eRod_Autonomous_Vehicle_2024 Project'::'eRod_Autonomous_Vehicle_2024'::'Operational Analysis'::'Operational Activities'::'Root Operational Activity'.'Report issues' { 
                        @CapellaID { eid = "2cdb4cf1-a4d0-437e-b342-cc6a9c1fb973"; } 
                        attribute :>> isMulticast = false; 
                        attribute :>> isMultireceive = false; 
                        attribute :>> kindOfRate = RateKind::Unspecified; 
                        attribute :>> interfaceName = "Display"; 
                    }  
                    connection '5a3af137-b554-411d-8d51-a26b3d748bf2' : OAInteraction 
                        connect source ::> 'eRod_Autonomous_Vehicle_2024 Project'::'eRod_Autonomous_Vehicle_2024'::'Operational Analysis'::'Operational Activities'::'Root Operational Activity'.'Report issues'
                        to  target ::> 'eRod_Autonomous_Vehicle_2024 Project'::'eRod_Autonomous_Vehicle_2024'::'Operational Analysis'::'Operational Activities'::'Root Operational Activity'.'Recieve issue' { 
                        @CapellaID { eid = "5a3af137-b554-411d-8d51-a26b3d748bf2"; } 
                        attribute :>> isMulticast = false; 
                        attribute :>> isMultireceive = false; 
                        attribute :>> kindOfRate = RateKind::Unspecified; 
                        attribute :>> interfaceName = "Feedback"; 
                    }  
                    connection 'e411a798-a889-4f53-9ec7-a427dbc97796' : OAInteraction 
                        connect source ::> 'eRod_Autonomous_Vehicle_2024 Project'::'eRod_Autonomous_Vehicle_2024'::'Operational Analysis'::'Operational Activities'::'Root Operational Activity'.'Get software update'
                        to  target ::> 'eRod_Autonomous_Vehicle_2024 Project'::'eRod_Autonomous_Vehicle_2024'::'Operational Analysis'::'Operational Activities'::'Root Operational Activity'.'Sporty drive' { 
                        @CapellaID { eid = "e411a798-a889-4f53-9ec7-a427dbc97796"; } 
                        attribute :>> isMulticast = false; 
                        attribute :>> isMultireceive = false; 
                        attribute :>> kindOfRate = RateKind::Unspecified; 
                        attribute :>> interfaceName = "Re-enable"; 
                    }  
                    connection '294cccd3-0efa-4370-b7f9-dbb6892bc5c6' : OAInteraction 
                        connect source ::> 'eRod_Autonomous_Vehicle_2024 Project'::'eRod_Autonomous_Vehicle_2024'::'Operational Analysis'::'Operational Activities'::'Root Operational Activity'.'Recieve issue'
                        to  target ::> 'eRod_Autonomous_Vehicle_2024 Project'::'eRod_Autonomous_Vehicle_2024'::'Operational Analysis'::'Operational Activities'::'Root Operational Activity'.'Provide solution' { 
                        @CapellaID { eid = "294cccd3-0efa-4370-b7f9-dbb6892bc5c6"; } 
                        attribute :>> isMulticast = false; 
                        attribute :>> isMultireceive = false; 
                        attribute :>> kindOfRate = RateKind::Unspecified; 
                        attribute :>> interfaceName = "Solve"; 
                    }  
                    connection '7e9ba078-437e-424e-a31b-379003b8d438' : OAInteraction 
                        connect source ::> 'eRod_Autonomous_Vehicle_2024 Project'::'eRod_Autonomous_Vehicle_2024'::'Operational Analysis'::'Operational Activities'::'Root Operational Activity'.'Provide solution'
                        to  target ::> 'eRod_Autonomous_Vehicle_2024 Project'::'eRod_Autonomous_Vehicle_2024'::'Operational Analysis'::'Operational Activities'::'Root Operational Activity'.'Informed Software update' { 
                        @CapellaID { eid = "7e9ba078-437e-424e-a31b-379003b8d438"; } 
                        attribute :>> isMulticast = false; 
                        attribute :>> isMultireceive = false; 
                        attribute :>> kindOfRate = RateKind::Unspecified; 
                        attribute :>> interfaceName = "Update"; 
                    }  
                    connection '5ac50b2c-b8c1-4f04-85ad-51b192d3012c' : OAInteraction 
                        connect source ::> 'eRod_Autonomous_Vehicle_2024 Project'::'eRod_Autonomous_Vehicle_2024'::'Operational Analysis'::'Operational Activities'::'Root Operational Activity'.'Informed Software update'
                        to  target ::> 'eRod_Autonomous_Vehicle_2024 Project'::'eRod_Autonomous_Vehicle_2024'::'Operational Analysis'::'Operational Activities'::'Root Operational Activity'.'Get software update' { 
                        @CapellaID { eid = "5ac50b2c-b8c1-4f04-85ad-51b192d3012c"; } 
                        attribute :>> isMulticast = false; 
                        attribute :>> isMultireceive = false; 
                        attribute :>> kindOfRate = RateKind::Unspecified; 
                        attribute :>> interfaceName = "Approval"; 
                    }  
                    connection '20bcc67f-ebd7-4369-a9c7-ff780c6f7238' : OAInteraction 
                        connect source ::> 'eRod_Autonomous_Vehicle_2024 Project'::'eRod_Autonomous_Vehicle_2024'::'Operational Analysis'::'Operational Activities'::'Root Operational Activity'.'Drive vehicle'
                        to  target ::> 'eRod_Autonomous_Vehicle_2024 Project'::'eRod_Autonomous_Vehicle_2024'::'Operational Analysis'::'Operational Activities'::'Root Operational Activity'.'Autonomous Driving' { 
                        @CapellaID { eid = "20bcc67f-ebd7-4369-a9c7-ff780c6f7238"; } 
                        attribute :>> isMulticast = false; 
                        attribute :>> isMultireceive = false; 
                        attribute :>> kindOfRate = RateKind::Unspecified; 
                        attribute :>> interfaceName = "Assign controls to vehicle"; 
                    }  
                    connection '287325bf-5771-47e4-a180-0e2bf3a565a4' : OAInteraction 
                        connect source ::> 'eRod_Autonomous_Vehicle_2024 Project'::'eRod_Autonomous_Vehicle_2024'::'Operational Analysis'::'Operational Activities'::'Root Operational Activity'.'Autonomous Driving'
                        to  target ::> 'eRod_Autonomous_Vehicle_2024 Project'::'eRod_Autonomous_Vehicle_2024'::'Operational Analysis'::'Operational Activities'::'Root Operational Activity'.'Drive vehicle' { 
                        @CapellaID { eid = "287325bf-5771-47e4-a180-0e2bf3a565a4"; } 
                        attribute :>> isMulticast = false; 
                        attribute :>> isMultireceive = false; 
                        attribute :>> kindOfRate = RateKind::Unspecified; 
                        attribute :>> interfaceName = "Take control of the vehicle"; 
                    }  
                    connection '29750a62-5ab7-4804-b101-3b4275a7ce75' : OAInteraction 
                        connect source ::> 'eRod_Autonomous_Vehicle_2024 Project'::'eRod_Autonomous_Vehicle_2024'::'Operational Analysis'::'Operational Activities'::'Root Operational Activity'.'Provide weather'
                        to  target ::> 'eRod_Autonomous_Vehicle_2024 Project'::'eRod_Autonomous_Vehicle_2024'::'Operational Analysis'::'Operational Activities'::'Root Operational Activity'.'Provide diverse terrain' { 
                        @CapellaID { eid = "29750a62-5ab7-4804-b101-3b4275a7ce75"; } 
                        attribute :>> isMulticast = false; 
                        attribute :>> isMultireceive = false; 
                        attribute :>> kindOfRate = RateKind::Unspecified; 
                        attribute :>> interfaceName = "Weather"; 
                    }  
                    connection 'c3d1dafa-945b-472a-a424-3658725cf30b' : OAInteraction 
                        connect source ::> 'eRod_Autonomous_Vehicle_2024 Project'::'eRod_Autonomous_Vehicle_2024'::'Operational Analysis'::'Operational Activities'::'Root Operational Activity'.'Provide diverse terrain'
                        to  target ::> 'eRod_Autonomous_Vehicle_2024 Project'::'eRod_Autonomous_Vehicle_2024'::'Operational Analysis'::'Operational Activities'::'Root Operational Activity'.'Drive vehicle' { 
                        @CapellaID { eid = "c3d1dafa-945b-472a-a424-3658725cf30b"; } 
                        attribute :>> isMulticast = false; 
                        attribute :>> isMultireceive = false; 
                        attribute :>> kindOfRate = RateKind::Unspecified; 
                        attribute :>> interfaceName = "Terrain"; 
                    }  
                    connection 'cc6a38c7-28c7-419f-8626-e1846d29a66a' : OAInteraction 
                        connect source ::> 'eRod_Autonomous_Vehicle_2024 Project'::'eRod_Autonomous_Vehicle_2024'::'Operational Analysis'::'Operational Activities'::'Root Operational Activity'.'Drive vehicle'
                        to  target ::> 'eRod_Autonomous_Vehicle_2024 Project'::'eRod_Autonomous_Vehicle_2024'::'Operational Analysis'::'Operational Activities'::'Root Operational Activity'.'Provide diverse terrain' { 
                        @CapellaID { eid = "cc6a38c7-28c7-419f-8626-e1846d29a66a"; } 
                        attribute :>> isMulticast = false; 
                        attribute :>> isMultireceive = false; 
                        attribute :>> kindOfRate = RateKind::Unspecified; 
                        attribute :>> interfaceName = "Location"; 
                    }  
                    connection 'be3b32c3-3470-40cf-b588-4345950201bb' : OAInteraction 
                        connect source ::> 'eRod_Autonomous_Vehicle_2024 Project'::'eRod_Autonomous_Vehicle_2024'::'Operational Analysis'::'Operational Activities'::'Root Operational Activity'.'Provide Object Locations'
                        to  target ::> 'eRod_Autonomous_Vehicle_2024 Project'::'eRod_Autonomous_Vehicle_2024'::'Operational Analysis'::'Operational Activities'::'Root Operational Activity'.'Drive vehicle' { 
                        @CapellaID { eid = "be3b32c3-3470-40cf-b588-4345950201bb"; } 
                        attribute :>> isMulticast = false; 
                        attribute :>> isMultireceive = false; 
                        attribute :>> kindOfRate = RateKind::Unspecified; 
                        attribute :>> interfaceName = "Objects"; 
                    }  
                    connection '3c056cac-2477-484b-a2fe-82eecf0cf136' : OAInteraction 
                        connect source ::> 'eRod_Autonomous_Vehicle_2024 Project'::'eRod_Autonomous_Vehicle_2024'::'Operational Analysis'::'Operational Activities'::'Root Operational Activity'.'Provide electricity'
                        to  target ::> 'eRod_Autonomous_Vehicle_2024 Project'::'eRod_Autonomous_Vehicle_2024'::'Operational Analysis'::'Operational Activities'::'Root Operational Activity'.'Connect charger' { 
                        @CapellaID { eid = "3c056cac-2477-484b-a2fe-82eecf0cf136"; } 
                        attribute :>> isMulticast = false; 
                        attribute :>> isMultireceive = false; 
                        attribute :>> kindOfRate = RateKind::Unspecified; 
                        attribute :>> interfaceName = "Electricity"; 
                    }  
                    connection 'b6784c26-e617-453a-a1b9-5a30f517cafd' : OAInteraction 
                        connect source ::> 'eRod_Autonomous_Vehicle_2024 Project'::'eRod_Autonomous_Vehicle_2024'::'Operational Analysis'::'Operational Activities'::'Root Operational Activity'.'Connect charger'
                        to  target ::> 'eRod_Autonomous_Vehicle_2024 Project'::'eRod_Autonomous_Vehicle_2024'::'Operational Analysis'::'Operational Activities'::'Root Operational Activity'.'Store energy' { 
                        @CapellaID { eid = "b6784c26-e617-453a-a1b9-5a30f517cafd"; } 
                        attribute :>> isMulticast = false; 
                        attribute :>> isMultireceive = false; 
                        attribute :>> kindOfRate = RateKind::Unspecified; 
                        attribute :>> interfaceName = "Electricity"; 
                    }  
                    connection '9feff163-a35d-4223-ae0e-01dc6fb16c8d' : OAInteraction 
                        connect source ::> 'eRod_Autonomous_Vehicle_2024 Project'::'eRod_Autonomous_Vehicle_2024'::'Operational Analysis'::'Operational Activities'::'Root Operational Activity'.'Activate Park Assist'
                        to  target ::> 'eRod_Autonomous_Vehicle_2024 Project'::'eRod_Autonomous_Vehicle_2024'::'Operational Analysis'::'Operational Activities'::'Root Operational Activity'.'Status and command indication' { 
                        @CapellaID { eid = "9feff163-a35d-4223-ae0e-01dc6fb16c8d"; } 
                        attribute :>> isMulticast = false; 
                        attribute :>> isMultireceive = false; 
                        attribute :>> kindOfRate = RateKind::Unspecified; 
                        attribute :>> interfaceName = "Activate"; 
                    }  
                    connection '76d64877-66fb-4538-a8bd-3257b01823e0' : OAInteraction 
                        connect source ::> 'eRod_Autonomous_Vehicle_2024 Project'::'eRod_Autonomous_Vehicle_2024'::'Operational Analysis'::'Operational Activities'::'Root Operational Activity'.'Activate Park Assist'
                        to  target ::> 'eRod_Autonomous_Vehicle_2024 Project'::'eRod_Autonomous_Vehicle_2024'::'Operational Analysis'::'Operational Activities'::'Root Operational Activity'.'Status and command indication' { 
                        @CapellaID { eid = "76d64877-66fb-4538-a8bd-3257b01823e0"; } 
                        attribute :>> isMulticast = false; 
                        attribute :>> isMultireceive = false; 
                        attribute :>> kindOfRate = RateKind::Unspecified; 
                        attribute :>> interfaceName = "Deactivate"; 
                    }  
                    connection 'cd03edc3-cf39-42eb-a3dc-4d00c66e61b7' : OAInteraction 
                        connect source ::> 'eRod_Autonomous_Vehicle_2024 Project'::'eRod_Autonomous_Vehicle_2024'::'Operational Analysis'::'Operational Activities'::'Root Operational Activity'.'Status and command indication'
                        to  target ::> 'eRod_Autonomous_Vehicle_2024 Project'::'eRod_Autonomous_Vehicle_2024'::'Operational Analysis'::'Operational Activities'::'Root Operational Activity'.'Park vehicle' { 
                        @CapellaID { eid = "cd03edc3-cf39-42eb-a3dc-4d00c66e61b7"; } 
                        attribute :>> isMulticast = false; 
                        attribute :>> isMultireceive = false; 
                        attribute :>> kindOfRate = RateKind::Unspecified; 
                        attribute :>> interfaceName = "Request parking"; 
                    }  
                    connection '4321f17e-98d3-48d2-807a-01582b0a7384' : OAInteraction 
                        connect source ::> 'eRod_Autonomous_Vehicle_2024 Project'::'eRod_Autonomous_Vehicle_2024'::'Operational Analysis'::'Operational Activities'::'Root Operational Activity'.'Avoid collision'
                        to  target ::> 'eRod_Autonomous_Vehicle_2024 Project'::'eRod_Autonomous_Vehicle_2024'::'Operational Analysis'::'Operational Activities'::'Root Operational Activity'.'Control braking' { 
                        @CapellaID { eid = "4321f17e-98d3-48d2-807a-01582b0a7384"; } 
                        attribute :>> isMulticast = false; 
                        attribute :>> isMultireceive = false; 
                        attribute :>> kindOfRate = RateKind::Unspecified; 
                        attribute :>> interfaceName = "Brake command"; 
                    }  
                    connection '442afbc1-4ced-42b6-bd7a-e15ba736d9a3' : OAInteraction 
                        connect source ::> 'eRod_Autonomous_Vehicle_2024 Project'::'eRod_Autonomous_Vehicle_2024'::'Operational Analysis'::'Operational Activities'::'Root Operational Activity'.'Avoid collision'
                        to  target ::> 'eRod_Autonomous_Vehicle_2024 Project'::'eRod_Autonomous_Vehicle_2024'::'Operational Analysis'::'Operational Activities'::'Root Operational Activity'.'Provide vehicle status' { 
                        @CapellaID { eid = "442afbc1-4ced-42b6-bd7a-e15ba736d9a3"; } 
                        attribute :>> isMulticast = false; 
                        attribute :>> isMultireceive = false; 
                        attribute :>> kindOfRate = RateKind::Unspecified; 
                        attribute :>> interfaceName = "Collsion Warning"; 
                    }  
                    connection '02ded698-869b-49b5-a269-0d727d86db2c' : OAInteraction 
                        connect source ::> 'eRod_Autonomous_Vehicle_2024 Project'::'eRod_Autonomous_Vehicle_2024'::'Operational Analysis'::'Operational Activities'::'Root Operational Activity'.'Provide vehicle status'
                        to  target ::> 'eRod_Autonomous_Vehicle_2024 Project'::'eRod_Autonomous_Vehicle_2024'::'Operational Analysis'::'Operational Activities'::'Root Operational Activity'.'Observe status' { 
                        @CapellaID { eid = "02ded698-869b-49b5-a269-0d727d86db2c"; } 
                        attribute :>> isMulticast = false; 
                        attribute :>> isMultireceive = false; 
                        attribute :>> kindOfRate = RateKind::Unspecified; 
                        attribute :>> interfaceName = "Status"; 
                    }  
                    connection '64c6a6f8-0c07-4837-9688-4f7957cb52a9' : OAInteraction 
                        connect source ::> 'eRod_Autonomous_Vehicle_2024 Project'::'eRod_Autonomous_Vehicle_2024'::'Operational Analysis'::'Operational Activities'::'Root Operational Activity'.'Locate targets'
                        to  target ::> 'eRod_Autonomous_Vehicle_2024 Project'::'eRod_Autonomous_Vehicle_2024'::'Operational Analysis'::'Operational Activities'::'Root Operational Activity'.'Avoid collision' { 
                        @CapellaID { eid = "64c6a6f8-0c07-4837-9688-4f7957cb52a9"; } 
                        attribute :>> isMulticast = false; 
                        attribute :>> isMultireceive = false; 
                        attribute :>> kindOfRate = RateKind::Unspecified; 
                        attribute :>> interfaceName = "Locate targets"; 
                    }  
                    connection 'c06c1227-c918-4524-b9b8-009a832b5232' : OAInteraction 
                        connect source ::> 'eRod_Autonomous_Vehicle_2024 Project'::'eRod_Autonomous_Vehicle_2024'::'Operational Analysis'::'Operational Activities'::'Root Operational Activity'.'Control braking'
                        to  target ::> 'eRod_Autonomous_Vehicle_2024 Project'::'eRod_Autonomous_Vehicle_2024'::'Operational Analysis'::'Operational Activities'::'Root Operational Activity'.'Deliver traction to surface' { 
                        @CapellaID { eid = "c06c1227-c918-4524-b9b8-009a832b5232"; } 
                        attribute :>> isMulticast = false; 
                        attribute :>> isMultireceive = false; 
                        attribute :>> kindOfRate = RateKind::Unspecified; 
                        attribute :>> interfaceName = "Deceleration"; 
                    }  
                    connection 'd728e19a-4bbe-47f5-aaa3-c80d75481f56' : OAInteraction 
                        connect source ::> 'eRod_Autonomous_Vehicle_2024 Project'::'eRod_Autonomous_Vehicle_2024'::'Operational Analysis'::'Operational Activities'::'Root Operational Activity'.'Maintain distance'
                        to  target ::> 'eRod_Autonomous_Vehicle_2024 Project'::'eRod_Autonomous_Vehicle_2024'::'Operational Analysis'::'Operational Activities'::'Root Operational Activity'.'Control braking' { 
                        @CapellaID { eid = "d728e19a-4bbe-47f5-aaa3-c80d75481f56"; } 
                        attribute :>> isMulticast = false; 
                        attribute :>> isMultireceive = false; 
                        attribute :>> kindOfRate = RateKind::Unspecified; 
                        attribute :>> interfaceName = "Active braking"; 
                    }  
                    connection '5a01edc2-42f9-40d5-a818-b5f0a5216281' : OAInteraction 
                        connect source ::> 'eRod_Autonomous_Vehicle_2024 Project'::'eRod_Autonomous_Vehicle_2024'::'Operational Analysis'::'Operational Activities'::'Root Operational Activity'.'Vehicle Command'
                        to  target ::> 'eRod_Autonomous_Vehicle_2024 Project'::'eRod_Autonomous_Vehicle_2024'::'Operational Analysis'::'Operational Activities'::'Root Operational Activity'.'Remote Operate Car' { 
                        @CapellaID { eid = "5a01edc2-42f9-40d5-a818-b5f0a5216281"; } 
                        attribute :>> isMulticast = false; 
                        attribute :>> isMultireceive = false; 
                        attribute :>> kindOfRate = RateKind::Unspecified; 
                        attribute :>> interfaceName = "Vehicle Commands"; 
                    }  
                    connection '3ab8c3d1-97d1-427d-b38b-8e979a3a3bde' : OAInteraction 
                        connect source ::> 'eRod_Autonomous_Vehicle_2024 Project'::'eRod_Autonomous_Vehicle_2024'::'Operational Analysis'::'Operational Activities'::'Root Operational Activity'.'Remote Operate Car'
                        to  target ::> 'eRod_Autonomous_Vehicle_2024 Project'::'eRod_Autonomous_Vehicle_2024'::'Operational Analysis'::'Operational Activities'::'Root Operational Activity'.'Park vehicle' { 
                        @CapellaID { eid = "3ab8c3d1-97d1-427d-b38b-8e979a3a3bde"; } 
                        attribute :>> isMulticast = false; 
                        attribute :>> isMultireceive = false; 
                        attribute :>> kindOfRate = RateKind::Unspecified; 
                        attribute :>> interfaceName = "Initiate Park"; 
                    }  
                    connection '28ee1538-7d17-4a8f-b43c-6c67de0ef9a0' : OAInteraction 
                        connect source ::> 'eRod_Autonomous_Vehicle_2024 Project'::'eRod_Autonomous_Vehicle_2024'::'Operational Analysis'::'Operational Activities'::'Root Operational Activity'.'Steer Wheels'
                        to  target ::> 'eRod_Autonomous_Vehicle_2024 Project'::'eRod_Autonomous_Vehicle_2024'::'Operational Analysis'::'Operational Activities'::'Root Operational Activity'.'Deliver traction to surface' { 
                        @CapellaID { eid = "28ee1538-7d17-4a8f-b43c-6c67de0ef9a0"; } 
                        attribute :>> isMulticast = false; 
                        attribute :>> isMultireceive = false; 
                        attribute :>> kindOfRate = RateKind::Unspecified; 
                        attribute :>> interfaceName = "Wheel Position"; 
                    }  
                    connection '8851dc30-4395-4b6c-b893-e49544d23f59' : OAInteraction 
                        connect source ::> 'eRod_Autonomous_Vehicle_2024 Project'::'eRod_Autonomous_Vehicle_2024'::'Operational Analysis'::'Operational Activities'::'Root Operational Activity'.'Park vehicle'
                        to  target ::> 'eRod_Autonomous_Vehicle_2024 Project'::'eRod_Autonomous_Vehicle_2024'::'Operational Analysis'::'Operational Activities'::'Root Operational Activity'.'Control braking' { 
                        @CapellaID { eid = "8851dc30-4395-4b6c-b893-e49544d23f59"; } 
                        attribute :>> isMulticast = false; 
                        attribute :>> isMultireceive = false; 
                        attribute :>> kindOfRate = RateKind::Unspecified; 
                        attribute :>> interfaceName = "Braking Commands"; 
                    }  
                    connection '6d432554-477c-4241-9a53-cd3c72fd0126' : OAInteraction 
                        connect source ::> 'eRod_Autonomous_Vehicle_2024 Project'::'eRod_Autonomous_Vehicle_2024'::'Operational Analysis'::'Operational Activities'::'Root Operational Activity'.'Park vehicle'
                        to  target ::> 'eRod_Autonomous_Vehicle_2024 Project'::'eRod_Autonomous_Vehicle_2024'::'Operational Analysis'::'Operational Activities'::'Root Operational Activity'.'Steer Wheels' { 
                        @CapellaID { eid = "6d432554-477c-4241-9a53-cd3c72fd0126"; } 
                        attribute :>> isMulticast = false; 
                        attribute :>> isMultireceive = false; 
                        attribute :>> kindOfRate = RateKind::Unspecified; 
                        attribute :>> interfaceName = "Steering Commands"; 
                    }  
                    connection '5bb84516-7881-44ea-8b6b-97e9b2816b1b' : OAInteraction 
                        connect source ::> 'eRod_Autonomous_Vehicle_2024 Project'::'eRod_Autonomous_Vehicle_2024'::'Operational Analysis'::'Operational Activities'::'Root Operational Activity'.'Deliver traction to surface'
                        to  target ::> 'eRod_Autonomous_Vehicle_2024 Project'::'eRod_Autonomous_Vehicle_2024'::'Operational Analysis'::'Operational Activities'::'Root Operational Activity'.'Provide diverse terrain' { 
                        @CapellaID { eid = "5bb84516-7881-44ea-8b6b-97e9b2816b1b"; } 
                        attribute :>> isMulticast = false; 
                        attribute :>> isMultireceive = false; 
                        attribute :>> kindOfRate = RateKind::Unspecified; 
                        attribute :>> interfaceName = "Traction"; 
                    }  
                    connection 'f002b530-4af5-4518-8415-51718e1e7d52' : OAInteraction 
                        connect source ::> 'eRod_Autonomous_Vehicle_2024 Project'::'eRod_Autonomous_Vehicle_2024'::'Operational Analysis'::'Operational Activities'::'Root Operational Activity'.'Provide Object Locations'
                        to  target ::> 'eRod_Autonomous_Vehicle_2024 Project'::'eRod_Autonomous_Vehicle_2024'::'Operational Analysis'::'Operational Activities'::'Root Operational Activity'.'Locate targets' { 
                        @CapellaID { eid = "f002b530-4af5-4518-8415-51718e1e7d52"; } 
                        attribute :>> isMulticast = false; 
                        attribute :>> isMultireceive = false; 
                        attribute :>> kindOfRate = RateKind::Unspecified; 
                        attribute :>> interfaceName = "Object Location"; 
                    }  
                    connection '3d30dfea-cc32-414e-9e96-fe69a71ce318' : OAInteraction 
                        connect source ::> 'eRod_Autonomous_Vehicle_2024 Project'::'eRod_Autonomous_Vehicle_2024'::'Operational Analysis'::'Operational Activities'::'Root Operational Activity'.'Status and command indication'
                        to  target ::> 'eRod_Autonomous_Vehicle_2024 Project'::'eRod_Autonomous_Vehicle_2024'::'Operational Analysis'::'Operational Activities'::'Root Operational Activity'.'Receive Status of Progess ' { 
                        @CapellaID { eid = "3d30dfea-cc32-414e-9e96-fe69a71ce318"; } 
                        attribute :>> isMulticast = false; 
                        attribute :>> isMultireceive = false; 
                        attribute :>> kindOfRate = RateKind::Unspecified; 
                        attribute :>> interfaceName = "Parking Status"; 
                    }  
                    ref :>> ownedFunctions =  ('eRod_Autonomous_Vehicle_2024 Project'::'eRod_Autonomous_Vehicle_2024'::'Operational Analysis'::'Operational Activities'::'Root Operational Activity'.'Drive on a race track',
                    'eRod_Autonomous_Vehicle_2024 Project'::'eRod_Autonomous_Vehicle_2024'::'Operational Analysis'::'Operational Activities'::'Root Operational Activity'.'Sporty drive',
                    'eRod_Autonomous_Vehicle_2024 Project'::'eRod_Autonomous_Vehicle_2024'::'Operational Analysis'::'Operational Activities'::'Root Operational Activity'.'Car racing experience',
                    'eRod_Autonomous_Vehicle_2024 Project'::'eRod_Autonomous_Vehicle_2024'::'Operational Analysis'::'Operational Activities'::'Root Operational Activity'.'Motor overheating warning ',
                    'eRod_Autonomous_Vehicle_2024 Project'::'eRod_Autonomous_Vehicle_2024'::'Operational Analysis'::'Operational Activities'::'Root Operational Activity'.'Get software update',
                    'eRod_Autonomous_Vehicle_2024 Project'::'eRod_Autonomous_Vehicle_2024'::'Operational Analysis'::'Operational Activities'::'Root Operational Activity'.'Report issues',
                    'eRod_Autonomous_Vehicle_2024 Project'::'eRod_Autonomous_Vehicle_2024'::'Operational Analysis'::'Operational Activities'::'Root Operational Activity'.'Recieve issue',
                    'eRod_Autonomous_Vehicle_2024 Project'::'eRod_Autonomous_Vehicle_2024'::'Operational Analysis'::'Operational Activities'::'Root Operational Activity'.'Provide solution',
                    'eRod_Autonomous_Vehicle_2024 Project'::'eRod_Autonomous_Vehicle_2024'::'Operational Analysis'::'Operational Activities'::'Root Operational Activity'.'Informed Software update',
                    'eRod_Autonomous_Vehicle_2024 Project'::'eRod_Autonomous_Vehicle_2024'::'Operational Analysis'::'Operational Activities'::'Root Operational Activity'.'Drive vehicle',
                    'eRod_Autonomous_Vehicle_2024 Project'::'eRod_Autonomous_Vehicle_2024'::'Operational Analysis'::'Operational Activities'::'Root Operational Activity'.'Autonomous Driving',
                    'eRod_Autonomous_Vehicle_2024 Project'::'eRod_Autonomous_Vehicle_2024'::'Operational Analysis'::'Operational Activities'::'Root Operational Activity'.'Provide diverse terrain',
                    'eRod_Autonomous_Vehicle_2024 Project'::'eRod_Autonomous_Vehicle_2024'::'Operational Analysis'::'Operational Activities'::'Root Operational Activity'.'Provide parking location',
                    'eRod_Autonomous_Vehicle_2024 Project'::'eRod_Autonomous_Vehicle_2024'::'Operational Analysis'::'Operational Activities'::'Root Operational Activity'.'Provide weather',
                    'eRod_Autonomous_Vehicle_2024 Project'::'eRod_Autonomous_Vehicle_2024'::'Operational Analysis'::'Operational Activities'::'Root Operational Activity'.'Provide Object Locations',
                    'eRod_Autonomous_Vehicle_2024 Project'::'eRod_Autonomous_Vehicle_2024'::'Operational Analysis'::'Operational Activities'::'Root Operational Activity'.'Provide electricity',
                    'eRod_Autonomous_Vehicle_2024 Project'::'eRod_Autonomous_Vehicle_2024'::'Operational Analysis'::'Operational Activities'::'Root Operational Activity'.'Store energy',
                    'eRod_Autonomous_Vehicle_2024 Project'::'eRod_Autonomous_Vehicle_2024'::'Operational Analysis'::'Operational Activities'::'Root Operational Activity'.'Connect charger',
                    'eRod_Autonomous_Vehicle_2024 Project'::'eRod_Autonomous_Vehicle_2024'::'Operational Analysis'::'Operational Activities'::'Root Operational Activity'.'Activate Park Assist',
                    'eRod_Autonomous_Vehicle_2024 Project'::'eRod_Autonomous_Vehicle_2024'::'Operational Analysis'::'Operational Activities'::'Root Operational Activity'.'Status and command indication',
                    'eRod_Autonomous_Vehicle_2024 Project'::'eRod_Autonomous_Vehicle_2024'::'Operational Analysis'::'Operational Activities'::'Root Operational Activity'.'Park vehicle',
                    'eRod_Autonomous_Vehicle_2024 Project'::'eRod_Autonomous_Vehicle_2024'::'Operational Analysis'::'Operational Activities'::'Root Operational Activity'.'Avoid collision',
                    'eRod_Autonomous_Vehicle_2024 Project'::'eRod_Autonomous_Vehicle_2024'::'Operational Analysis'::'Operational Activities'::'Root Operational Activity'.'Control braking',
                    'eRod_Autonomous_Vehicle_2024 Project'::'eRod_Autonomous_Vehicle_2024'::'Operational Analysis'::'Operational Activities'::'Root Operational Activity'.'Provide vehicle status',
                    'eRod_Autonomous_Vehicle_2024 Project'::'eRod_Autonomous_Vehicle_2024'::'Operational Analysis'::'Operational Activities'::'Root Operational Activity'.'Observe status',
                    'eRod_Autonomous_Vehicle_2024 Project'::'eRod_Autonomous_Vehicle_2024'::'Operational Analysis'::'Operational Activities'::'Root Operational Activity'.'Locate targets',
                    'eRod_Autonomous_Vehicle_2024 Project'::'eRod_Autonomous_Vehicle_2024'::'Operational Analysis'::'Operational Activities'::'Root Operational Activity'.'Deliver traction to surface',
                    'eRod_Autonomous_Vehicle_2024 Project'::'eRod_Autonomous_Vehicle_2024'::'Operational Analysis'::'Operational Activities'::'Root Operational Activity'.'Maintain distance',
                    'eRod_Autonomous_Vehicle_2024 Project'::'eRod_Autonomous_Vehicle_2024'::'Operational Analysis'::'Operational Activities'::'Root Operational Activity'.'Vehicle Command',
                    'eRod_Autonomous_Vehicle_2024 Project'::'eRod_Autonomous_Vehicle_2024'::'Operational Analysis'::'Operational Activities'::'Root Operational Activity'.'Remote Operate Car',
                    'eRod_Autonomous_Vehicle_2024 Project'::'eRod_Autonomous_Vehicle_2024'::'Operational Analysis'::'Operational Activities'::'Root Operational Activity'.'Steer Wheels',
                    'eRod_Autonomous_Vehicle_2024 Project'::'eRod_Autonomous_Vehicle_2024'::'Operational Analysis'::'Operational Activities'::'Root Operational Activity'.'Receive Status of Progess '); 
                    ref :>> ownedFunctionalExchanges =  ('eRod_Autonomous_Vehicle_2024 Project'::'eRod_Autonomous_Vehicle_2024'::'Operational Analysis'::'Operational Activities'::'Root Operational Activity'.'977b5caa-70f3-4c7e-b032-362c17973ba4',
                    'eRod_Autonomous_Vehicle_2024 Project'::'eRod_Autonomous_Vehicle_2024'::'Operational Analysis'::'Operational Activities'::'Root Operational Activity'.'4e7d42f3-4119-417c-9f11-95b7198c264e',
                    'eRod_Autonomous_Vehicle_2024 Project'::'eRod_Autonomous_Vehicle_2024'::'Operational Analysis'::'Operational Activities'::'Root Operational Activity'.'48b9100c-c194-4d69-9a4e-13fd46674196',
                    'eRod_Autonomous_Vehicle_2024 Project'::'eRod_Autonomous_Vehicle_2024'::'Operational Analysis'::'Operational Activities'::'Root Operational Activity'.'2cdb4cf1-a4d0-437e-b342-cc6a9c1fb973',
                    'eRod_Autonomous_Vehicle_2024 Project'::'eRod_Autonomous_Vehicle_2024'::'Operational Analysis'::'Operational Activities'::'Root Operational Activity'.'5a3af137-b554-411d-8d51-a26b3d748bf2',
                    'eRod_Autonomous_Vehicle_2024 Project'::'eRod_Autonomous_Vehicle_2024'::'Operational Analysis'::'Operational Activities'::'Root Operational Activity'.'e411a798-a889-4f53-9ec7-a427dbc97796',
                    'eRod_Autonomous_Vehicle_2024 Project'::'eRod_Autonomous_Vehicle_2024'::'Operational Analysis'::'Operational Activities'::'Root Operational Activity'.'294cccd3-0efa-4370-b7f9-dbb6892bc5c6',
                    'eRod_Autonomous_Vehicle_2024 Project'::'eRod_Autonomous_Vehicle_2024'::'Operational Analysis'::'Operational Activities'::'Root Operational Activity'.'7e9ba078-437e-424e-a31b-379003b8d438',
                    'eRod_Autonomous_Vehicle_2024 Project'::'eRod_Autonomous_Vehicle_2024'::'Operational Analysis'::'Operational Activities'::'Root Operational Activity'.'5ac50b2c-b8c1-4f04-85ad-51b192d3012c',
                    'eRod_Autonomous_Vehicle_2024 Project'::'eRod_Autonomous_Vehicle_2024'::'Operational Analysis'::'Operational Activities'::'Root Operational Activity'.'20bcc67f-ebd7-4369-a9c7-ff780c6f7238',
                    'eRod_Autonomous_Vehicle_2024 Project'::'eRod_Autonomous_Vehicle_2024'::'Operational Analysis'::'Operational Activities'::'Root Operational Activity'.'287325bf-5771-47e4-a180-0e2bf3a565a4',
                    'eRod_Autonomous_Vehicle_2024 Project'::'eRod_Autonomous_Vehicle_2024'::'Operational Analysis'::'Operational Activities'::'Root Operational Activity'.'29750a62-5ab7-4804-b101-3b4275a7ce75',
                    'eRod_Autonomous_Vehicle_2024 Project'::'eRod_Autonomous_Vehicle_2024'::'Operational Analysis'::'Operational Activities'::'Root Operational Activity'.'c3d1dafa-945b-472a-a424-3658725cf30b',
                    'eRod_Autonomous_Vehicle_2024 Project'::'eRod_Autonomous_Vehicle_2024'::'Operational Analysis'::'Operational Activities'::'Root Operational Activity'.'cc6a38c7-28c7-419f-8626-e1846d29a66a',
                    'eRod_Autonomous_Vehicle_2024 Project'::'eRod_Autonomous_Vehicle_2024'::'Operational Analysis'::'Operational Activities'::'Root Operational Activity'.'be3b32c3-3470-40cf-b588-4345950201bb',
                    'eRod_Autonomous_Vehicle_2024 Project'::'eRod_Autonomous_Vehicle_2024'::'Operational Analysis'::'Operational Activities'::'Root Operational Activity'.'3c056cac-2477-484b-a2fe-82eecf0cf136',
                    'eRod_Autonomous_Vehicle_2024 Project'::'eRod_Autonomous_Vehicle_2024'::'Operational Analysis'::'Operational Activities'::'Root Operational Activity'.'b6784c26-e617-453a-a1b9-5a30f517cafd',
                    'eRod_Autonomous_Vehicle_2024 Project'::'eRod_Autonomous_Vehicle_2024'::'Operational Analysis'::'Operational Activities'::'Root Operational Activity'.'9feff163-a35d-4223-ae0e-01dc6fb16c8d',
                    'eRod_Autonomous_Vehicle_2024 Project'::'eRod_Autonomous_Vehicle_2024'::'Operational Analysis'::'Operational Activities'::'Root Operational Activity'.'76d64877-66fb-4538-a8bd-3257b01823e0',
                    'eRod_Autonomous_Vehicle_2024 Project'::'eRod_Autonomous_Vehicle_2024'::'Operational Analysis'::'Operational Activities'::'Root Operational Activity'.'cd03edc3-cf39-42eb-a3dc-4d00c66e61b7',
                    'eRod_Autonomous_Vehicle_2024 Project'::'eRod_Autonomous_Vehicle_2024'::'Operational Analysis'::'Operational Activities'::'Root Operational Activity'.'4321f17e-98d3-48d2-807a-01582b0a7384',
                    'eRod_Autonomous_Vehicle_2024 Project'::'eRod_Autonomous_Vehicle_2024'::'Operational Analysis'::'Operational Activities'::'Root Operational Activity'.'442afbc1-4ced-42b6-bd7a-e15ba736d9a3',
                    'eRod_Autonomous_Vehicle_2024 Project'::'eRod_Autonomous_Vehicle_2024'::'Operational Analysis'::'Operational Activities'::'Root Operational Activity'.'02ded698-869b-49b5-a269-0d727d86db2c',
                    'eRod_Autonomous_Vehicle_2024 Project'::'eRod_Autonomous_Vehicle_2024'::'Operational Analysis'::'Operational Activities'::'Root Operational Activity'.'64c6a6f8-0c07-4837-9688-4f7957cb52a9',
                    'eRod_Autonomous_Vehicle_2024 Project'::'eRod_Autonomous_Vehicle_2024'::'Operational Analysis'::'Operational Activities'::'Root Operational Activity'.'c06c1227-c918-4524-b9b8-009a832b5232',
                    'eRod_Autonomous_Vehicle_2024 Project'::'eRod_Autonomous_Vehicle_2024'::'Operational Analysis'::'Operational Activities'::'Root Operational Activity'.'d728e19a-4bbe-47f5-aaa3-c80d75481f56',
                    'eRod_Autonomous_Vehicle_2024 Project'::'eRod_Autonomous_Vehicle_2024'::'Operational Analysis'::'Operational Activities'::'Root Operational Activity'.'5a01edc2-42f9-40d5-a818-b5f0a5216281',
                    'eRod_Autonomous_Vehicle_2024 Project'::'eRod_Autonomous_Vehicle_2024'::'Operational Analysis'::'Operational Activities'::'Root Operational Activity'.'3ab8c3d1-97d1-427d-b38b-8e979a3a3bde',
                    'eRod_Autonomous_Vehicle_2024 Project'::'eRod_Autonomous_Vehicle_2024'::'Operational Analysis'::'Operational Activities'::'Root Operational Activity'.'28ee1538-7d17-4a8f-b43c-6c67de0ef9a0',
                    'eRod_Autonomous_Vehicle_2024 Project'::'eRod_Autonomous_Vehicle_2024'::'Operational Analysis'::'Operational Activities'::'Root Operational Activity'.'8851dc30-4395-4b6c-b893-e49544d23f59',
                    'eRod_Autonomous_Vehicle_2024 Project'::'eRod_Autonomous_Vehicle_2024'::'Operational Analysis'::'Operational Activities'::'Root Operational Activity'.'6d432554-477c-4241-9a53-cd3c72fd0126',
                    'eRod_Autonomous_Vehicle_2024 Project'::'eRod_Autonomous_Vehicle_2024'::'Operational Analysis'::'Operational Activities'::'Root Operational Activity'.'5bb84516-7881-44ea-8b6b-97e9b2816b1b',
                    'eRod_Autonomous_Vehicle_2024 Project'::'eRod_Autonomous_Vehicle_2024'::'Operational Analysis'::'Operational Activities'::'Root Operational Activity'.'f002b530-4af5-4518-8415-51718e1e7d52',
                    'eRod_Autonomous_Vehicle_2024 Project'::'eRod_Autonomous_Vehicle_2024'::'Operational Analysis'::'Operational Activities'::'Root Operational Activity'.'3d30dfea-cc32-414e-9e96-fe69a71ce318'); 
                }  
            } 
            package  'Interfaces' {
                @PackageMeta {
                    type = "InterfacePkg";
                } 
                @CapellaID { eid = "78c2262c-0f26-48ea-a369-94873f89fcf8"; } 
            } 
            package  'Data' {
                @PackageMeta {
                    type = "DataPkg";
                } 
                @CapellaID { eid = "46efeabd-45c3-452f-8f4e-e33a3eaeb399"; } 
                item 'Driver' : Class { 
                    @CapellaID { eid = "80d68fea-033d-49e2-b081-3f36b9be311b"; } 
                    attribute :>> isAbstract = false; 
                    attribute :>> isFinal = false; 
                    attribute :>> isPrimitive = false; 
                }  
                item 'eRod' :> 'eRod_Autonomous_Vehicle_2024 Project'::'eRod_Autonomous_Vehicle_2024'::'Operational Analysis'::'Data'::'Race' { 
                    @CapellaID { eid = "d0294740-3d43-4526-b331-4cf53a63b686"; } 
                    attribute :>> isAbstract = false; 
                    attribute :>> isFinal = false; 
                    attribute :>> isPrimitive = false; 
                     
                }  
                item 'Race' : Class { 
                    @CapellaID { eid = "7399ce45-4628-4eb1-a518-8101dab2210c"; } 
                    attribute :>> isAbstract = false; 
                    attribute :>> isFinal = false; 
                    attribute :>> isPrimitive = false; 
                }  
                item 'Motor overheating issues' : Class { 
                    @CapellaID { eid = "7f3a8a88-1b65-4f19-89e2-c4c370adf690"; } 
                    attribute :>> isAbstract = false; 
                    attribute :>> isFinal = false; 
                    attribute :>> isPrimitive = false; 
                }  
                item 'Customer service' : Class { 
                    @CapellaID { eid = "61602a98-d7ee-4b28-b79f-2bf7aa469b21"; } 
                    attribute :>> isAbstract = false; 
                    attribute :>> isFinal = false; 
                    attribute :>> isPrimitive = false; 
                }  
                item 'Engineering department' : Class { 
                    @CapellaID { eid = "eee990e1-08f0-449a-9e4f-5016d87ece88"; } 
                    attribute :>> isAbstract = false; 
                    attribute :>> isFinal = false; 
                    attribute :>> isPrimitive = false; 
                }  
                item 'Software update' : Class { 
                    @CapellaID { eid = "ee377a2c-65fe-4479-9f35-b13f98f4b6b3"; } 
                    attribute :>> isAbstract = false; 
                    attribute :>> isFinal = false; 
                    attribute :>> isPrimitive = false; 
                }  
                item 'Design a cooling system ' : Class { 
                    @CapellaID { eid = "4cccf4a6-5be3-4a64-80f4-3c7955fbe144"; } 
                    attribute :>> isAbstract = false; 
                    attribute :>> isFinal = false; 
                    attribute :>> isPrimitive = false; 
                }  
                item 'New motor' : Class { 
                    @CapellaID { eid = "9ef76d96-ae60-4076-a3a5-bebed723bea8"; } 
                    attribute :>> isAbstract = false; 
                    attribute :>> isFinal = false; 
                    attribute :>> isPrimitive = false; 
                }  
                item 'No car racing capability' : Class { 
                    @CapellaID { eid = "36593e48-6a8d-4860-ae35-590db675d689"; } 
                    attribute :>> isAbstract = false; 
                    attribute :>> isFinal = false; 
                    attribute :>> isPrimitive = false; 
                }  
            } 
            package  'Operational Capabilities' {
                @PackageMeta {
                    type = "OperationalCapabilityPkg";
                } 
                @CapellaID { eid = "6c92aa0d-fe35-476b-a662-b86777b723c3"; } 
                use case 'Always connected' : OperationalCapability { 
                    @CapellaID { eid = "605452f0-7a9e-4c5c-8b15-1497cd9a9aa4"; } 
                    include 'eRod_Autonomous_Vehicle_2024 Project'::'eRod_Autonomous_Vehicle_2024'::'Operational Analysis'::'Operational Capabilities'::'remote update'; 
                    actor 'Driver' = 'eRod_Autonomous_Vehicle_2024 Project'::'eRod_Autonomous_Vehicle_2024'::'Operational Analysis'::'Operational Entities'::'Driver'; 
                    actor 'eRod' = 'eRod_Autonomous_Vehicle_2024 Project'::'eRod_Autonomous_Vehicle_2024'::'Operational Analysis'::'Operational Entities'::'Sport-Offroad Buggies'.'eRod'; 
                }  
                use case 'Personalized driving experience' : OperationalCapability { 
                    @CapellaID { eid = "249768bd-3263-47c4-988b-35db85ed2b9b"; } 
                }  
                use case 'Predictive maintenance' : OperationalCapability { 
                    @CapellaID { eid = "09a630e7-efea-4ec3-9e3b-f2ec29f5f38c"; } 
                    actor 'Driver' = 'eRod_Autonomous_Vehicle_2024 Project'::'eRod_Autonomous_Vehicle_2024'::'Operational Analysis'::'Operational Entities'::'Driver'; 
                    actor 'eRod' = 'eRod_Autonomous_Vehicle_2024 Project'::'eRod_Autonomous_Vehicle_2024'::'Operational Analysis'::'Operational Entities'::'Sport-Offroad Buggies'.'eRod'; 
                }  
                use case 'remote update' : OperationalCapability { 
                    @CapellaID { eid = "30e5cc1c-a534-4bfe-b3c8-4367bd6a656e"; } 
                    attribute :>> summary = "Provide the capability of remote update to solve some problem in short-term or optimize the performance"; 
                    ref action '78e11b41-d966-422d-84b2-cb1e71ffb336' = 'eRod_Autonomous_Vehicle_2024 Project'::'eRod_Autonomous_Vehicle_2024'::'Operational Analysis'::'Operational Activities'::'Root Operational Activity'.'Remote update'; 
                    actor 'Driver' = 'eRod_Autonomous_Vehicle_2024 Project'::'eRod_Autonomous_Vehicle_2024'::'Operational Analysis'::'Operational Entities'::'Driver'; 
                    actor 'eRod' = 'eRod_Autonomous_Vehicle_2024 Project'::'eRod_Autonomous_Vehicle_2024'::'Operational Analysis'::'Operational Entities'::'Sport-Offroad Buggies'.'eRod'; 
                    actor 'eRod Manufactor' = 'eRod_Autonomous_Vehicle_2024 Project'::'eRod_Autonomous_Vehicle_2024'::'Operational Analysis'::'Operational Entities'::'eRod Manufactor'; 
                     
                }  
                use case 'Autonmous Driving' : OperationalCapability { 
                    @CapellaID { eid = "65a7f55e-69f3-4963-af85-2a818f114c92"; } 
                    ref action '5c3cc85d-2b9a-4bad-b4d4-2b876efffca4' = 'eRod_Autonomous_Vehicle_2024 Project'::'eRod_Autonomous_Vehicle_2024'::'Operational Analysis'::'Operational Activities'::'Root Operational Activity'.'Activate Autonmous'; 
                    ref action 'a29b5acd-91e0-45d9-874e-370fd948b69b' = 'eRod_Autonomous_Vehicle_2024 Project'::'eRod_Autonomous_Vehicle_2024'::'Operational Analysis'::'Operational Activities'::'Root Operational Activity'.'Resume Driver Control'; 
                    actor 'eRod' = 'eRod_Autonomous_Vehicle_2024 Project'::'eRod_Autonomous_Vehicle_2024'::'Operational Analysis'::'Operational Entities'::'Sport-Offroad Buggies'.'eRod'; 
                    actor 'Driver' = 'eRod_Autonomous_Vehicle_2024 Project'::'eRod_Autonomous_Vehicle_2024'::'Operational Analysis'::'Operational Entities'::'Driver'; 
                }  
                use case 'Shorter model cycles' : OperationalCapability { 
                    @CapellaID { eid = "04b0645f-6811-41b4-944b-dc2357022f18"; } 
                    attribute :>> summary = "Using simulations to shorten the design duration"; 
                    actor 'eRod' = 'eRod_Autonomous_Vehicle_2024 Project'::'eRod_Autonomous_Vehicle_2024'::'Operational Analysis'::'Operational Entities'::'Sport-Offroad Buggies'.'eRod'; 
                }  
                use case 'Better customer/driving experience in the car' : OperationalCapability { 
                    @CapellaID { eid = "6bf9f1b8-1e87-4059-9324-3f36fe390875"; } 
                    include 'eRod_Autonomous_Vehicle_2024 Project'::'eRod_Autonomous_Vehicle_2024'::'Operational Analysis'::'Operational Capabilities'::'Personalized driving experience'; 
                    actor 'eRod' = 'eRod_Autonomous_Vehicle_2024 Project'::'eRod_Autonomous_Vehicle_2024'::'Operational Analysis'::'Operational Entities'::'Sport-Offroad Buggies'.'eRod'; 
                    actor 'Driver' = 'eRod_Autonomous_Vehicle_2024 Project'::'eRod_Autonomous_Vehicle_2024'::'Operational Analysis'::'Operational Entities'::'Driver'; 
                     
                }  
                use case 'Security' : OperationalCapability { 
                    @CapellaID { eid = "5ab1ef65-6fd9-4fee-a5c3-a357ae48caae"; } 
                    actor 'Driver' = 'eRod_Autonomous_Vehicle_2024 Project'::'eRod_Autonomous_Vehicle_2024'::'Operational Analysis'::'Operational Entities'::'Driver'; 
                }  
                use case 'Improve car buying experience' : OperationalCapability { 
                    @CapellaID { eid = "9a86018f-c908-40cb-b44e-1cf96af46263"; } 
                    actor 'Driver' = 'eRod_Autonomous_Vehicle_2024 Project'::'eRod_Autonomous_Vehicle_2024'::'Operational Analysis'::'Operational Entities'::'Driver'; 
                }  
                use case 'Car racing' : OperationalCapability { 
                    @CapellaID { eid = "5c199b57-4e29-43d4-9333-55bffecf91ef"; } 
                    ref action '8100eaed-e48d-4eaa-a9cf-46f333e18b9d' = 'eRod_Autonomous_Vehicle_2024 Project'::'eRod_Autonomous_Vehicle_2024'::'Operational Analysis'::'Operational Activities'::'Root Operational Activity'.'Car racing'; 
                    actor 'eRod' = 'eRod_Autonomous_Vehicle_2024 Project'::'eRod_Autonomous_Vehicle_2024'::'Operational Analysis'::'Operational Entities'::'Sport-Offroad Buggies'.'eRod'; 
                    actor 'Driver' = 'eRod_Autonomous_Vehicle_2024 Project'::'eRod_Autonomous_Vehicle_2024'::'Operational Analysis'::'Operational Entities'::'Driver'; 
                     
                }  
                use case 'Provide Active Driving Assistance' : OperationalCapability { 
                    @CapellaID { eid = "e2582057-e4b0-4ba9-a9d3-c61f5a9f62cd"; } 
                    include 'eRod_Autonomous_Vehicle_2024 Project'::'eRod_Autonomous_Vehicle_2024'::'Operational Analysis'::'Operational Capabilities'::'Avoid Collision'; 
                    include 'eRod_Autonomous_Vehicle_2024 Project'::'eRod_Autonomous_Vehicle_2024'::'Operational Analysis'::'Operational Capabilities'::'Maintain Distance from Lead Car'; 
                    include 'eRod_Autonomous_Vehicle_2024 Project'::'eRod_Autonomous_Vehicle_2024'::'Operational Analysis'::'Operational Capabilities'::'Provide Lane Keep Assistance'; 
                    include 'eRod_Autonomous_Vehicle_2024 Project'::'eRod_Autonomous_Vehicle_2024'::'Operational Analysis'::'Operational Capabilities'::'Protect Pedestrians'; 
                    include 'eRod_Autonomous_Vehicle_2024 Project'::'eRod_Autonomous_Vehicle_2024'::'Operational Analysis'::'Operational Capabilities'::'Provide Easy Parking Assistance'; 
                    include 'eRod_Autonomous_Vehicle_2024 Project'::'eRod_Autonomous_Vehicle_2024'::'Operational Analysis'::'Operational Capabilities'::'Recognize Traffic Signs'; 
                    actor 'Driver' = 'eRod_Autonomous_Vehicle_2024 Project'::'eRod_Autonomous_Vehicle_2024'::'Operational Analysis'::'Operational Entities'::'Driver'; 
                    actor 'eRod' = 'eRod_Autonomous_Vehicle_2024 Project'::'eRod_Autonomous_Vehicle_2024'::'Operational Analysis'::'Operational Entities'::'Sport-Offroad Buggies'.'eRod'; 
                }  
                use case 'Avoid Collision' : OperationalCapability { 
                    @CapellaID { eid = "47d2f90b-6a42-45a3-b723-4d589fb607a8"; } 
                }  
                use case 'Maintain Distance from Lead Car' : OperationalCapability { 
                    @CapellaID { eid = "3e1bd299-b4de-4913-8d1c-0407b128f45c"; } 
                }  
                use case 'Provide Lane Keep Assistance' : OperationalCapability { 
                    @CapellaID { eid = "302ea470-52d5-42a8-8a3c-dbc9ffd95b41"; } 
                }  
                use case 'Protect Pedestrians' : OperationalCapability { 
                    @CapellaID { eid = "359518b6-9274-4106-a4a1-12da91bb8a14"; } 
                }  
                use case 'Provide Easy Parking Assistance' : OperationalCapability { 
                    @CapellaID { eid = "5fe72592-2309-4166-97df-3f6d8065faee"; } 
                }  
                use case 'Recognize Traffic Signs' : OperationalCapability { 
                    @CapellaID { eid = "95f87500-c1f0-4d73-9fcc-625903f67ac7"; } 
                }  
                use case 'Remote Park' : OperationalCapability { 
                    @CapellaID { eid = "4f330c04-920f-4a17-b18f-9a05d4e54f05"; } 
                    actor 'Remote Driver' = 'eRod_Autonomous_Vehicle_2024 Project'::'eRod_Autonomous_Vehicle_2024'::'Operational Analysis'::'Operational Entities'::'Remote Driver'; 
                }  
            } 
            package  'Roles' {
                @PackageMeta {
                    type = "RolePkg";
                } 
                @CapellaID { eid = "ee6318ed-521c-43f9-a6b9-74b30e7c8353"; } 
            } 
            package  'Operational Entities' {
                @PackageMeta {
                    type = "EntityPkg";
                } 
                @CapellaID { eid = "bff25c1a-4be1-4d4c-bd19-3414c5758753"; } 
                part 'Driver' : Entity  { 
                    doc /*
                    <!DOCTYPE html>
                    <html>
                    <head>
                        <title>Driver Description</title>
                    </head>
                    <body>
                    <h1>Driver</h1>

                    <p>A driver, in the context of transportation, refers to an individual who operates a motor vehicle to transport people or goods from one location to another. Drivers are responsible for ensuring the safe and efficient operation of the vehicle, following traffic laws, and delivering passengers or goods to their intended destination.</p>

                    <p>There are various types of drivers, including professional drivers, such as truck drivers, taxi drivers, and delivery drivers, who specialize in transporting goods or people for commercial purposes. Additionally, private individuals who operate their personal vehicles for personal transportation purposes are also considered drivers.</p>

                    <p>Common responsibilities of a driver may include:</p>
                    <ul>
                        <li>Following traffic laws and regulations.</li>
                        <li>Maintaining the vehicle in good condition.</li>
                        <li>Ensuring passenger or cargo safety during transportation.</li>
                        <li>Planning and navigating the most efficient routes.</li>
                        <li>Communicating with clients, passengers, or dispatchers as necessary.</li>
                    </ul>

                    <p>Skills and qualities that are desirable in a driver include good communication and interpersonal skills, a strong sense of responsibility, excellent driving abilities, adaptability to changing road conditions, and a commitment to safety.</p>

                    <p>References:</p>
                    <p>[1] Merriam-Webster. (n.d.). Driver. In <i>Merriam-Webster.com</i>. Retrieved [date], from https://www.merriam-webster.com/dictionary/driver</p>
                    <p>[2] Occupational Outlook Handbook. (n.d.). Delivery truck drivers and driver/sales workers. In <i>Bureau of Labor Statistics</i>. Retrieved [date], from https://www.bls.gov/ooh/transportation-and-material-moving/delivery-truck-drivers-and-driver-sales-workers.htm</p>
                    <p>[3] United States Department of Labor. (n.d.). Taxi drivers and chauffeurs. In <i>Bureau of Labor Statistics</i>. Retrieved [date], from https://www.bls.gov/ooh/transportation-and-material-moving/taxi-drivers-and-chauffeurs.htm</p>

                    </body>
                    </html>
                    */ 
                    @CapellaID { eid = "1f8e2605-19c2-4ab4-a8b6-46d74e18ba68"; } 
                    attribute :>> isAbstract = false; 
                    attribute :>> isActor = true; 
                    attribute :>> isHuman = true; 
                    allocation '20321332-c7a6-42e2-a020-c5935bd7f6fe' : ComponentFunctionalAllocation
                        allocate function ::> 'eRod_Autonomous_Vehicle_2024 Project'::'eRod_Autonomous_Vehicle_2024'::'Operational Analysis'::'Operational Activities'::'Root Operational Activity'.'Drive on a race track'
                        to component ::> 'eRod_Autonomous_Vehicle_2024 Project'::'eRod_Autonomous_Vehicle_2024'::'Operational Analysis'::'Operational Entities'::'Driver';
                    perform 'eRod_Autonomous_Vehicle_2024 Project'::'eRod_Autonomous_Vehicle_2024'::'Operational Analysis'::'Operational Activities'::'Root Operational Activity'.'Drive on a race track' ; 
                    allocation '9b944156-1317-4fbf-ae83-3283b981e1ec' : ComponentFunctionalAllocation
                        allocate function ::> 'eRod_Autonomous_Vehicle_2024 Project'::'eRod_Autonomous_Vehicle_2024'::'Operational Analysis'::'Operational Activities'::'Root Operational Activity'.'Car racing experience'
                        to component ::> 'eRod_Autonomous_Vehicle_2024 Project'::'eRod_Autonomous_Vehicle_2024'::'Operational Analysis'::'Operational Entities'::'Driver';
                    perform 'eRod_Autonomous_Vehicle_2024 Project'::'eRod_Autonomous_Vehicle_2024'::'Operational Analysis'::'Operational Activities'::'Root Operational Activity'.'Car racing experience' ; 
                    allocation '5f72f061-fd9d-435b-a2e5-8142a1c9d6b3' : ComponentFunctionalAllocation
                        allocate function ::> 'eRod_Autonomous_Vehicle_2024 Project'::'eRod_Autonomous_Vehicle_2024'::'Operational Analysis'::'Operational Activities'::'Root Operational Activity'.'Report issues'
                        to component ::> 'eRod_Autonomous_Vehicle_2024 Project'::'eRod_Autonomous_Vehicle_2024'::'Operational Analysis'::'Operational Entities'::'Driver';
                    perform 'eRod_Autonomous_Vehicle_2024 Project'::'eRod_Autonomous_Vehicle_2024'::'Operational Analysis'::'Operational Activities'::'Root Operational Activity'.'Report issues' ; 
                    allocation 'f18ca081-64c5-4586-b21a-3a54c1fbf6e5' : ComponentFunctionalAllocation
                        allocate function ::> 'eRod_Autonomous_Vehicle_2024 Project'::'eRod_Autonomous_Vehicle_2024'::'Operational Analysis'::'Operational Activities'::'Root Operational Activity'.'Informed Software update'
                        to component ::> 'eRod_Autonomous_Vehicle_2024 Project'::'eRod_Autonomous_Vehicle_2024'::'Operational Analysis'::'Operational Entities'::'Driver';
                    perform 'eRod_Autonomous_Vehicle_2024 Project'::'eRod_Autonomous_Vehicle_2024'::'Operational Analysis'::'Operational Activities'::'Root Operational Activity'.'Informed Software update' ; 
                    allocation '576c5c83-4328-4452-b0e6-a0bf0eca53d0' : ComponentFunctionalAllocation
                        allocate function ::> 'eRod_Autonomous_Vehicle_2024 Project'::'eRod_Autonomous_Vehicle_2024'::'Operational Analysis'::'Operational Activities'::'Root Operational Activity'.'Drive vehicle'
                        to component ::> 'eRod_Autonomous_Vehicle_2024 Project'::'eRod_Autonomous_Vehicle_2024'::'Operational Analysis'::'Operational Entities'::'Driver';
                    perform 'eRod_Autonomous_Vehicle_2024 Project'::'eRod_Autonomous_Vehicle_2024'::'Operational Analysis'::'Operational Activities'::'Root Operational Activity'.'Drive vehicle' ; 
                    allocation '5b6e7b79-d77d-4523-abe8-bacd1b2da676' : ComponentFunctionalAllocation
                        allocate function ::> 'eRod_Autonomous_Vehicle_2024 Project'::'eRod_Autonomous_Vehicle_2024'::'Operational Analysis'::'Operational Activities'::'Root Operational Activity'.'Connect charger'
                        to component ::> 'eRod_Autonomous_Vehicle_2024 Project'::'eRod_Autonomous_Vehicle_2024'::'Operational Analysis'::'Operational Entities'::'Driver';
                    perform 'eRod_Autonomous_Vehicle_2024 Project'::'eRod_Autonomous_Vehicle_2024'::'Operational Analysis'::'Operational Activities'::'Root Operational Activity'.'Connect charger' ; 
                    allocation 'bc530b20-ede7-440b-bddd-2427122e7207' : ComponentFunctionalAllocation
                        allocate function ::> 'eRod_Autonomous_Vehicle_2024 Project'::'eRod_Autonomous_Vehicle_2024'::'Operational Analysis'::'Operational Activities'::'Root Operational Activity'.'Activate Park Assist'
                        to component ::> 'eRod_Autonomous_Vehicle_2024 Project'::'eRod_Autonomous_Vehicle_2024'::'Operational Analysis'::'Operational Entities'::'Driver';
                    perform 'eRod_Autonomous_Vehicle_2024 Project'::'eRod_Autonomous_Vehicle_2024'::'Operational Analysis'::'Operational Activities'::'Root Operational Activity'.'Activate Park Assist' ; 
                    allocation 'aad41a59-489c-408d-9941-347acf145a1c' : ComponentFunctionalAllocation
                        allocate function ::> 'eRod_Autonomous_Vehicle_2024 Project'::'eRod_Autonomous_Vehicle_2024'::'Operational Analysis'::'Operational Activities'::'Root Operational Activity'.'Observe status'
                        to component ::> 'eRod_Autonomous_Vehicle_2024 Project'::'eRod_Autonomous_Vehicle_2024'::'Operational Analysis'::'Operational Entities'::'Driver';
                    perform 'eRod_Autonomous_Vehicle_2024 Project'::'eRod_Autonomous_Vehicle_2024'::'Operational Analysis'::'Operational Activities'::'Root Operational Activity'.'Observe status' ; 
                    ref :>> ownedFunctionalAllocation =  ('eRod_Autonomous_Vehicle_2024 Project'::'eRod_Autonomous_Vehicle_2024'::'Operational Analysis'::'Operational Entities'::'Driver'.'20321332-c7a6-42e2-a020-c5935bd7f6fe',
                    'eRod_Autonomous_Vehicle_2024 Project'::'eRod_Autonomous_Vehicle_2024'::'Operational Analysis'::'Operational Entities'::'Driver'.'9b944156-1317-4fbf-ae83-3283b981e1ec',
                    'eRod_Autonomous_Vehicle_2024 Project'::'eRod_Autonomous_Vehicle_2024'::'Operational Analysis'::'Operational Entities'::'Driver'.'5f72f061-fd9d-435b-a2e5-8142a1c9d6b3',
                    'eRod_Autonomous_Vehicle_2024 Project'::'eRod_Autonomous_Vehicle_2024'::'Operational Analysis'::'Operational Entities'::'Driver'.'f18ca081-64c5-4586-b21a-3a54c1fbf6e5',
                    'eRod_Autonomous_Vehicle_2024 Project'::'eRod_Autonomous_Vehicle_2024'::'Operational Analysis'::'Operational Entities'::'Driver'.'576c5c83-4328-4452-b0e6-a0bf0eca53d0',
                    'eRod_Autonomous_Vehicle_2024 Project'::'eRod_Autonomous_Vehicle_2024'::'Operational Analysis'::'Operational Entities'::'Driver'.'5b6e7b79-d77d-4523-abe8-bacd1b2da676',
                    'eRod_Autonomous_Vehicle_2024 Project'::'eRod_Autonomous_Vehicle_2024'::'Operational Analysis'::'Operational Entities'::'Driver'.'bc530b20-ede7-440b-bddd-2427122e7207',
                    'eRod_Autonomous_Vehicle_2024 Project'::'eRod_Autonomous_Vehicle_2024'::'Operational Analysis'::'Operational Entities'::'Driver'.'aad41a59-489c-408d-9941-347acf145a1c'); 
                }  
                part 'Sport-Offroad Buggies' : Entity  { 
                    @CapellaID { eid = "c2925aef-d92c-42f5-ac2b-0a2e7d0f2656"; } 
                    attribute :>> isAbstract = false; 
                    attribute :>> isActor = false; 
                    attribute :>> isHuman = false; 
                    part 'eRod' : Entity  { 
                        @CapellaID { eid = "cbce1a45-881c-4bd2-bf11-d1537484636b"; } 
                        attribute :>> isAbstract = false; 
                        attribute :>> isActor = false; 
                        attribute :>> isHuman = false; 
                        allocation '4cedb7b4-af11-41a6-9d8b-82622721e4c5' : ComponentFunctionalAllocation
                            allocate function ::> 'eRod_Autonomous_Vehicle_2024 Project'::'eRod_Autonomous_Vehicle_2024'::'Operational Analysis'::'Operational Activities'::'Root Operational Activity'.'Sporty drive'
                            to component ::> 'eRod_Autonomous_Vehicle_2024 Project'::'eRod_Autonomous_Vehicle_2024'::'Operational Analysis'::'Operational Entities'::'Sport-Offroad Buggies'.'eRod';
                        perform 'eRod_Autonomous_Vehicle_2024 Project'::'eRod_Autonomous_Vehicle_2024'::'Operational Analysis'::'Operational Activities'::'Root Operational Activity'.'Sporty drive' ; 
                        allocation 'c9cf2eb4-223d-43ee-9872-176ded14098a' : ComponentFunctionalAllocation
                            allocate function ::> 'eRod_Autonomous_Vehicle_2024 Project'::'eRod_Autonomous_Vehicle_2024'::'Operational Analysis'::'Operational Activities'::'Root Operational Activity'.'Motor overheating warning '
                            to component ::> 'eRod_Autonomous_Vehicle_2024 Project'::'eRod_Autonomous_Vehicle_2024'::'Operational Analysis'::'Operational Entities'::'Sport-Offroad Buggies'.'eRod';
                        perform 'eRod_Autonomous_Vehicle_2024 Project'::'eRod_Autonomous_Vehicle_2024'::'Operational Analysis'::'Operational Activities'::'Root Operational Activity'.'Motor overheating warning ' ; 
                        allocation '1a83f4e5-0a7b-484a-a2df-850d6ecacb4b' : ComponentFunctionalAllocation
                            allocate function ::> 'eRod_Autonomous_Vehicle_2024 Project'::'eRod_Autonomous_Vehicle_2024'::'Operational Analysis'::'Operational Activities'::'Root Operational Activity'.'Get software update'
                            to component ::> 'eRod_Autonomous_Vehicle_2024 Project'::'eRod_Autonomous_Vehicle_2024'::'Operational Analysis'::'Operational Entities'::'Sport-Offroad Buggies'.'eRod';
                        perform 'eRod_Autonomous_Vehicle_2024 Project'::'eRod_Autonomous_Vehicle_2024'::'Operational Analysis'::'Operational Activities'::'Root Operational Activity'.'Get software update' ; 
                        allocation '046abe56-d8f8-4693-ba2b-2852278c3f2c' : ComponentFunctionalAllocation
                            allocate function ::> 'eRod_Autonomous_Vehicle_2024 Project'::'eRod_Autonomous_Vehicle_2024'::'Operational Analysis'::'Operational Activities'::'Root Operational Activity'.'Autonomous Driving'
                            to component ::> 'eRod_Autonomous_Vehicle_2024 Project'::'eRod_Autonomous_Vehicle_2024'::'Operational Analysis'::'Operational Entities'::'Sport-Offroad Buggies'.'eRod';
                        perform 'eRod_Autonomous_Vehicle_2024 Project'::'eRod_Autonomous_Vehicle_2024'::'Operational Analysis'::'Operational Activities'::'Root Operational Activity'.'Autonomous Driving' ; 
                        ref :>> ownedFunctionalAllocation =  ('eRod_Autonomous_Vehicle_2024 Project'::'eRod_Autonomous_Vehicle_2024'::'Operational Analysis'::'Operational Entities'::'Sport-Offroad Buggies'.'eRod'.'4cedb7b4-af11-41a6-9d8b-82622721e4c5',
                        'eRod_Autonomous_Vehicle_2024 Project'::'eRod_Autonomous_Vehicle_2024'::'Operational Analysis'::'Operational Entities'::'Sport-Offroad Buggies'.'eRod'.'c9cf2eb4-223d-43ee-9872-176ded14098a',
                        'eRod_Autonomous_Vehicle_2024 Project'::'eRod_Autonomous_Vehicle_2024'::'Operational Analysis'::'Operational Entities'::'Sport-Offroad Buggies'.'eRod'.'1a83f4e5-0a7b-484a-a2df-850d6ecacb4b',
                        'eRod_Autonomous_Vehicle_2024 Project'::'eRod_Autonomous_Vehicle_2024'::'Operational Analysis'::'Operational Entities'::'Sport-Offroad Buggies'.'eRod'.'046abe56-d8f8-4693-ba2b-2852278c3f2c'); 
                    }  
                    ref :>> ownedEntities =  ('eRod_Autonomous_Vehicle_2024 Project'::'eRod_Autonomous_Vehicle_2024'::'Operational Analysis'::'Operational Entities'::'Sport-Offroad Buggies'.'eRod'); 
                }  
                part 'eRod Manufactor' : Entity  { 
                    @CapellaID { eid = "a6797faa-09a0-4d11-8162-04705e82f2ac"; } 
                    attribute :>> isAbstract = false; 
                    attribute :>> isActor = true; 
                    attribute :>> isHuman = true; 
                    allocation '2a9394c1-84e6-4714-af83-e9844d0806e6' : ComponentFunctionalAllocation
                        allocate function ::> 'eRod_Autonomous_Vehicle_2024 Project'::'eRod_Autonomous_Vehicle_2024'::'Operational Analysis'::'Operational Activities'::'Root Operational Activity'.'Recieve issue'
                        to component ::> 'eRod_Autonomous_Vehicle_2024 Project'::'eRod_Autonomous_Vehicle_2024'::'Operational Analysis'::'Operational Entities'::'eRod Manufactor';
                    perform 'eRod_Autonomous_Vehicle_2024 Project'::'eRod_Autonomous_Vehicle_2024'::'Operational Analysis'::'Operational Activities'::'Root Operational Activity'.'Recieve issue' ; 
                    allocation 'eab2f47d-9b29-4c33-a8b2-5481a410cf57' : ComponentFunctionalAllocation
                        allocate function ::> 'eRod_Autonomous_Vehicle_2024 Project'::'eRod_Autonomous_Vehicle_2024'::'Operational Analysis'::'Operational Activities'::'Root Operational Activity'.'Provide solution'
                        to component ::> 'eRod_Autonomous_Vehicle_2024 Project'::'eRod_Autonomous_Vehicle_2024'::'Operational Analysis'::'Operational Entities'::'eRod Manufactor';
                    perform 'eRod_Autonomous_Vehicle_2024 Project'::'eRod_Autonomous_Vehicle_2024'::'Operational Analysis'::'Operational Activities'::'Root Operational Activity'.'Provide solution' ; 
                    ref :>> ownedFunctionalAllocation =  ('eRod_Autonomous_Vehicle_2024 Project'::'eRod_Autonomous_Vehicle_2024'::'Operational Analysis'::'Operational Entities'::'eRod Manufactor'.'2a9394c1-84e6-4714-af83-e9844d0806e6',
                    'eRod_Autonomous_Vehicle_2024 Project'::'eRod_Autonomous_Vehicle_2024'::'Operational Analysis'::'Operational Entities'::'eRod Manufactor'.'eab2f47d-9b29-4c33-a8b2-5481a410cf57'); 
                }  
                part 'Environment' : Entity  { 
                    @CapellaID { eid = "95c7bed5-d7f3-4492-873e-bb477167f533"; } 
                    attribute :>> isAbstract = false; 
                    attribute :>> isActor = false; 
                    attribute :>> isHuman = false; 
                    part 'Terrain/Roads' : Entity  { 
                        @CapellaID { eid = "29ef924b-1663-4ee5-bf29-02a9187e6f37"; } 
                        attribute :>> isAbstract = false; 
                        attribute :>> isActor = false; 
                        attribute :>> isHuman = false; 
                        allocation 'c2319949-4d7c-41b9-a6eb-84ef0a4cfdbc' : ComponentFunctionalAllocation
                            allocate function ::> 'eRod_Autonomous_Vehicle_2024 Project'::'eRod_Autonomous_Vehicle_2024'::'Operational Analysis'::'Operational Activities'::'Root Operational Activity'.'Provide diverse terrain'
                            to component ::> 'eRod_Autonomous_Vehicle_2024 Project'::'eRod_Autonomous_Vehicle_2024'::'Operational Analysis'::'Operational Entities'::'Environment'.'Terrain/Roads';
                        perform 'eRod_Autonomous_Vehicle_2024 Project'::'eRod_Autonomous_Vehicle_2024'::'Operational Analysis'::'Operational Activities'::'Root Operational Activity'.'Provide diverse terrain' ; 
                        allocation '6b4cf163-db8f-4ef3-91c9-06264cd442bb' : ComponentFunctionalAllocation
                            allocate function ::> 'eRod_Autonomous_Vehicle_2024 Project'::'eRod_Autonomous_Vehicle_2024'::'Operational Analysis'::'Operational Activities'::'Root Operational Activity'.'Provide parking location'
                            to component ::> 'eRod_Autonomous_Vehicle_2024 Project'::'eRod_Autonomous_Vehicle_2024'::'Operational Analysis'::'Operational Entities'::'Environment'.'Terrain/Roads';
                        perform 'eRod_Autonomous_Vehicle_2024 Project'::'eRod_Autonomous_Vehicle_2024'::'Operational Analysis'::'Operational Activities'::'Root Operational Activity'.'Provide parking location' ; 
                        ref :>> ownedFunctionalAllocation =  ('eRod_Autonomous_Vehicle_2024 Project'::'eRod_Autonomous_Vehicle_2024'::'Operational Analysis'::'Operational Entities'::'Environment'.'Terrain/Roads'.'c2319949-4d7c-41b9-a6eb-84ef0a4cfdbc',
                        'eRod_Autonomous_Vehicle_2024 Project'::'eRod_Autonomous_Vehicle_2024'::'Operational Analysis'::'Operational Entities'::'Environment'.'Terrain/Roads'.'6b4cf163-db8f-4ef3-91c9-06264cd442bb'); 
                    }  
                    part 'Weather' : Entity  { 
                        @CapellaID { eid = "e75b843e-057b-4c7e-a12f-562732133629"; } 
                        attribute :>> isAbstract = false; 
                        attribute :>> isActor = false; 
                        attribute :>> isHuman = false; 
                        allocation '55282e8f-e4c0-4b64-8eca-a936d72972a5' : ComponentFunctionalAllocation
                            allocate function ::> 'eRod_Autonomous_Vehicle_2024 Project'::'eRod_Autonomous_Vehicle_2024'::'Operational Analysis'::'Operational Activities'::'Root Operational Activity'.'Provide weather'
                            to component ::> 'eRod_Autonomous_Vehicle_2024 Project'::'eRod_Autonomous_Vehicle_2024'::'Operational Analysis'::'Operational Entities'::'Environment'.'Weather';
                        perform 'eRod_Autonomous_Vehicle_2024 Project'::'eRod_Autonomous_Vehicle_2024'::'Operational Analysis'::'Operational Activities'::'Root Operational Activity'.'Provide weather' ; 
                        ref :>> ownedFunctionalAllocation =  ('eRod_Autonomous_Vehicle_2024 Project'::'eRod_Autonomous_Vehicle_2024'::'Operational Analysis'::'Operational Entities'::'Environment'.'Weather'.'55282e8f-e4c0-4b64-8eca-a936d72972a5'); 
                    }  
                    part 'External Objects' : Entity  { 
                        @CapellaID { eid = "7484650d-96fe-42e1-896f-0baf07ea4c62"; } 
                        attribute :>> isAbstract = false; 
                        attribute :>> isActor = false; 
                        attribute :>> isHuman = false; 
                        allocation 'd31cd8c9-19c2-435e-bfa1-e296dc13e325' : ComponentFunctionalAllocation
                            allocate function ::> 'eRod_Autonomous_Vehicle_2024 Project'::'eRod_Autonomous_Vehicle_2024'::'Operational Analysis'::'Operational Activities'::'Root Operational Activity'.'Provide Object Locations'
                            to component ::> 'eRod_Autonomous_Vehicle_2024 Project'::'eRod_Autonomous_Vehicle_2024'::'Operational Analysis'::'Operational Entities'::'Environment'.'External Objects';
                        perform 'eRod_Autonomous_Vehicle_2024 Project'::'eRod_Autonomous_Vehicle_2024'::'Operational Analysis'::'Operational Activities'::'Root Operational Activity'.'Provide Object Locations' ; 
                        ref :>> ownedFunctionalAllocation =  ('eRod_Autonomous_Vehicle_2024 Project'::'eRod_Autonomous_Vehicle_2024'::'Operational Analysis'::'Operational Entities'::'Environment'.'External Objects'.'d31cd8c9-19c2-435e-bfa1-e296dc13e325'); 
                    }  
                    ref :>> ownedEntities =  ('eRod_Autonomous_Vehicle_2024 Project'::'eRod_Autonomous_Vehicle_2024'::'Operational Analysis'::'Operational Entities'::'Environment'.'Terrain/Roads',
                    'eRod_Autonomous_Vehicle_2024 Project'::'eRod_Autonomous_Vehicle_2024'::'Operational Analysis'::'Operational Entities'::'Environment'.'Weather',
                    'eRod_Autonomous_Vehicle_2024 Project'::'eRod_Autonomous_Vehicle_2024'::'Operational Analysis'::'Operational Entities'::'Environment'.'External Objects'); 
                }  
                part 'Energy' : Entity  { 
                    @CapellaID { eid = "db36ef14-a4d4-4867-a9b3-b5b5917b23e7"; } 
                    attribute :>> isAbstract = false; 
                    attribute :>> isActor = false; 
                    attribute :>> isHuman = false; 
                    allocation 'f449168a-e0fa-4ca2-bf6d-bb1c0bd4d09d' : ComponentFunctionalAllocation
                        allocate function ::> 'eRod_Autonomous_Vehicle_2024 Project'::'eRod_Autonomous_Vehicle_2024'::'Operational Analysis'::'Operational Activities'::'Root Operational Activity'.'Provide electricity'
                        to component ::> 'eRod_Autonomous_Vehicle_2024 Project'::'eRod_Autonomous_Vehicle_2024'::'Operational Analysis'::'Operational Entities'::'Energy';
                    perform 'eRod_Autonomous_Vehicle_2024 Project'::'eRod_Autonomous_Vehicle_2024'::'Operational Analysis'::'Operational Activities'::'Root Operational Activity'.'Provide electricity' ; 
                    ref :>> ownedFunctionalAllocation =  ('eRod_Autonomous_Vehicle_2024 Project'::'eRod_Autonomous_Vehicle_2024'::'Operational Analysis'::'Operational Entities'::'Energy'.'f449168a-e0fa-4ca2-bf6d-bb1c0bd4d09d'); 
                }  
                part 'eRod' : Entity  { 
                    @CapellaID { eid = "7bab29d3-ee69-4491-bd08-e717d42134ab"; } 
                    attribute :>> isAbstract = false; 
                    attribute :>> isActor = false; 
                    attribute :>> isHuman = false; 
                    allocation '208db779-9fc7-4fc7-84b5-e449c7307ecc' : ComponentFunctionalAllocation
                        allocate function ::> 'eRod_Autonomous_Vehicle_2024 Project'::'eRod_Autonomous_Vehicle_2024'::'Operational Analysis'::'Operational Activities'::'Root Operational Activity'.'Store energy'
                        to component ::> 'eRod_Autonomous_Vehicle_2024 Project'::'eRod_Autonomous_Vehicle_2024'::'Operational Analysis'::'Operational Entities'::'eRod';
                    perform 'eRod_Autonomous_Vehicle_2024 Project'::'eRod_Autonomous_Vehicle_2024'::'Operational Analysis'::'Operational Activities'::'Root Operational Activity'.'Store energy' ; 
                    allocation '9f4f5fa9-47b4-4d82-8bc0-b8e94921946f' : ComponentFunctionalAllocation
                        allocate function ::> 'eRod_Autonomous_Vehicle_2024 Project'::'eRod_Autonomous_Vehicle_2024'::'Operational Analysis'::'Operational Activities'::'Root Operational Activity'.'Status and command indication'
                        to component ::> 'eRod_Autonomous_Vehicle_2024 Project'::'eRod_Autonomous_Vehicle_2024'::'Operational Analysis'::'Operational Entities'::'eRod';
                    perform 'eRod_Autonomous_Vehicle_2024 Project'::'eRod_Autonomous_Vehicle_2024'::'Operational Analysis'::'Operational Activities'::'Root Operational Activity'.'Status and command indication' ; 
                    allocation '90257e13-41ed-48dd-85b5-e6e4639d9ff8' : ComponentFunctionalAllocation
                        allocate function ::> 'eRod_Autonomous_Vehicle_2024 Project'::'eRod_Autonomous_Vehicle_2024'::'Operational Analysis'::'Operational Activities'::'Root Operational Activity'.'Park vehicle'
                        to component ::> 'eRod_Autonomous_Vehicle_2024 Project'::'eRod_Autonomous_Vehicle_2024'::'Operational Analysis'::'Operational Entities'::'eRod';
                    perform 'eRod_Autonomous_Vehicle_2024 Project'::'eRod_Autonomous_Vehicle_2024'::'Operational Analysis'::'Operational Activities'::'Root Operational Activity'.'Park vehicle' ; 
                    allocation '3f8ad469-8d7e-4eb0-8388-00d6b4779b78' : ComponentFunctionalAllocation
                        allocate function ::> 'eRod_Autonomous_Vehicle_2024 Project'::'eRod_Autonomous_Vehicle_2024'::'Operational Analysis'::'Operational Activities'::'Root Operational Activity'.'Avoid collision'
                        to component ::> 'eRod_Autonomous_Vehicle_2024 Project'::'eRod_Autonomous_Vehicle_2024'::'Operational Analysis'::'Operational Entities'::'eRod';
                    perform 'eRod_Autonomous_Vehicle_2024 Project'::'eRod_Autonomous_Vehicle_2024'::'Operational Analysis'::'Operational Activities'::'Root Operational Activity'.'Avoid collision' ; 
                    allocation 'db2bb600-41df-4b4e-ada8-026fbe7a9f66' : ComponentFunctionalAllocation
                        allocate function ::> 'eRod_Autonomous_Vehicle_2024 Project'::'eRod_Autonomous_Vehicle_2024'::'Operational Analysis'::'Operational Activities'::'Root Operational Activity'.'Control braking'
                        to component ::> 'eRod_Autonomous_Vehicle_2024 Project'::'eRod_Autonomous_Vehicle_2024'::'Operational Analysis'::'Operational Entities'::'eRod';
                    perform 'eRod_Autonomous_Vehicle_2024 Project'::'eRod_Autonomous_Vehicle_2024'::'Operational Analysis'::'Operational Activities'::'Root Operational Activity'.'Control braking' ; 
                    allocation 'a9a736d2-b221-4044-96e9-decf1f07b0b3' : ComponentFunctionalAllocation
                        allocate function ::> 'eRod_Autonomous_Vehicle_2024 Project'::'eRod_Autonomous_Vehicle_2024'::'Operational Analysis'::'Operational Activities'::'Root Operational Activity'.'Provide vehicle status'
                        to component ::> 'eRod_Autonomous_Vehicle_2024 Project'::'eRod_Autonomous_Vehicle_2024'::'Operational Analysis'::'Operational Entities'::'eRod';
                    perform 'eRod_Autonomous_Vehicle_2024 Project'::'eRod_Autonomous_Vehicle_2024'::'Operational Analysis'::'Operational Activities'::'Root Operational Activity'.'Provide vehicle status' ; 
                    allocation '10b1823f-4ddd-4674-9b01-27c5c07454fa' : ComponentFunctionalAllocation
                        allocate function ::> 'eRod_Autonomous_Vehicle_2024 Project'::'eRod_Autonomous_Vehicle_2024'::'Operational Analysis'::'Operational Activities'::'Root Operational Activity'.'Locate targets'
                        to component ::> 'eRod_Autonomous_Vehicle_2024 Project'::'eRod_Autonomous_Vehicle_2024'::'Operational Analysis'::'Operational Entities'::'eRod';
                    perform 'eRod_Autonomous_Vehicle_2024 Project'::'eRod_Autonomous_Vehicle_2024'::'Operational Analysis'::'Operational Activities'::'Root Operational Activity'.'Locate targets' ; 
                    allocation '047377a2-b57c-4171-a87d-e29eb83ed91b' : ComponentFunctionalAllocation
                        allocate function ::> 'eRod_Autonomous_Vehicle_2024 Project'::'eRod_Autonomous_Vehicle_2024'::'Operational Analysis'::'Operational Activities'::'Root Operational Activity'.'Deliver traction to surface'
                        to component ::> 'eRod_Autonomous_Vehicle_2024 Project'::'eRod_Autonomous_Vehicle_2024'::'Operational Analysis'::'Operational Entities'::'eRod';
                    perform 'eRod_Autonomous_Vehicle_2024 Project'::'eRod_Autonomous_Vehicle_2024'::'Operational Analysis'::'Operational Activities'::'Root Operational Activity'.'Deliver traction to surface' ; 
                    allocation 'a9cc1191-cdd9-4c62-83d0-1728731a7219' : ComponentFunctionalAllocation
                        allocate function ::> 'eRod_Autonomous_Vehicle_2024 Project'::'eRod_Autonomous_Vehicle_2024'::'Operational Analysis'::'Operational Activities'::'Root Operational Activity'.'Maintain distance'
                        to component ::> 'eRod_Autonomous_Vehicle_2024 Project'::'eRod_Autonomous_Vehicle_2024'::'Operational Analysis'::'Operational Entities'::'eRod';
                    perform 'eRod_Autonomous_Vehicle_2024 Project'::'eRod_Autonomous_Vehicle_2024'::'Operational Analysis'::'Operational Activities'::'Root Operational Activity'.'Maintain distance' ; 
                    allocation 'c2954043-fb97-42b1-8951-c5a43cbf8e91' : ComponentFunctionalAllocation
                        allocate function ::> 'eRod_Autonomous_Vehicle_2024 Project'::'eRod_Autonomous_Vehicle_2024'::'Operational Analysis'::'Operational Activities'::'Root Operational Activity'.'Remote Operate Car'
                        to component ::> 'eRod_Autonomous_Vehicle_2024 Project'::'eRod_Autonomous_Vehicle_2024'::'Operational Analysis'::'Operational Entities'::'eRod';
                    perform 'eRod_Autonomous_Vehicle_2024 Project'::'eRod_Autonomous_Vehicle_2024'::'Operational Analysis'::'Operational Activities'::'Root Operational Activity'.'Remote Operate Car' ; 
                    allocation '7203626a-d4b4-4ed6-b96f-1f043d0d1d3f' : ComponentFunctionalAllocation
                        allocate function ::> 'eRod_Autonomous_Vehicle_2024 Project'::'eRod_Autonomous_Vehicle_2024'::'Operational Analysis'::'Operational Activities'::'Root Operational Activity'.'Steer Wheels'
                        to component ::> 'eRod_Autonomous_Vehicle_2024 Project'::'eRod_Autonomous_Vehicle_2024'::'Operational Analysis'::'Operational Entities'::'eRod';
                    perform 'eRod_Autonomous_Vehicle_2024 Project'::'eRod_Autonomous_Vehicle_2024'::'Operational Analysis'::'Operational Activities'::'Root Operational Activity'.'Steer Wheels' ; 
                    ref :>> ownedFunctionalAllocation =  ('eRod_Autonomous_Vehicle_2024 Project'::'eRod_Autonomous_Vehicle_2024'::'Operational Analysis'::'Operational Entities'::'eRod'.'208db779-9fc7-4fc7-84b5-e449c7307ecc',
                    'eRod_Autonomous_Vehicle_2024 Project'::'eRod_Autonomous_Vehicle_2024'::'Operational Analysis'::'Operational Entities'::'eRod'.'9f4f5fa9-47b4-4d82-8bc0-b8e94921946f',
                    'eRod_Autonomous_Vehicle_2024 Project'::'eRod_Autonomous_Vehicle_2024'::'Operational Analysis'::'Operational Entities'::'eRod'.'90257e13-41ed-48dd-85b5-e6e4639d9ff8',
                    'eRod_Autonomous_Vehicle_2024 Project'::'eRod_Autonomous_Vehicle_2024'::'Operational Analysis'::'Operational Entities'::'eRod'.'3f8ad469-8d7e-4eb0-8388-00d6b4779b78',
                    'eRod_Autonomous_Vehicle_2024 Project'::'eRod_Autonomous_Vehicle_2024'::'Operational Analysis'::'Operational Entities'::'eRod'.'db2bb600-41df-4b4e-ada8-026fbe7a9f66',
                    'eRod_Autonomous_Vehicle_2024 Project'::'eRod_Autonomous_Vehicle_2024'::'Operational Analysis'::'Operational Entities'::'eRod'.'a9a736d2-b221-4044-96e9-decf1f07b0b3',
                    'eRod_Autonomous_Vehicle_2024 Project'::'eRod_Autonomous_Vehicle_2024'::'Operational Analysis'::'Operational Entities'::'eRod'.'10b1823f-4ddd-4674-9b01-27c5c07454fa',
                    'eRod_Autonomous_Vehicle_2024 Project'::'eRod_Autonomous_Vehicle_2024'::'Operational Analysis'::'Operational Entities'::'eRod'.'047377a2-b57c-4171-a87d-e29eb83ed91b',
                    'eRod_Autonomous_Vehicle_2024 Project'::'eRod_Autonomous_Vehicle_2024'::'Operational Analysis'::'Operational Entities'::'eRod'.'a9cc1191-cdd9-4c62-83d0-1728731a7219',
                    'eRod_Autonomous_Vehicle_2024 Project'::'eRod_Autonomous_Vehicle_2024'::'Operational Analysis'::'Operational Entities'::'eRod'.'c2954043-fb97-42b1-8951-c5a43cbf8e91',
                    'eRod_Autonomous_Vehicle_2024 Project'::'eRod_Autonomous_Vehicle_2024'::'Operational Analysis'::'Operational Entities'::'eRod'.'7203626a-d4b4-4ed6-b96f-1f043d0d1d3f'); 
                }  
                part 'Remote Driver' : Entity  { 
                    @CapellaID { eid = "58abf625-5c7d-40fb-989f-2fc177d5fb00"; } 
                    attribute :>> isAbstract = false; 
                    attribute :>> isActor = true; 
                    attribute :>> isHuman = true; 
                    allocation 'eff29269-6858-400b-8174-073907889f74' : ComponentFunctionalAllocation
                        allocate function ::> 'eRod_Autonomous_Vehicle_2024 Project'::'eRod_Autonomous_Vehicle_2024'::'Operational Analysis'::'Operational Activities'::'Root Operational Activity'.'Receive Status of Progess '
                        to component ::> 'eRod_Autonomous_Vehicle_2024 Project'::'eRod_Autonomous_Vehicle_2024'::'Operational Analysis'::'Operational Entities'::'Remote Driver';
                    perform 'eRod_Autonomous_Vehicle_2024 Project'::'eRod_Autonomous_Vehicle_2024'::'Operational Analysis'::'Operational Activities'::'Root Operational Activity'.'Receive Status of Progess ' ; 
                    allocation '0da12271-3df6-4156-87d8-0d24b47f536f' : ComponentFunctionalAllocation
                        allocate function ::> 'eRod_Autonomous_Vehicle_2024 Project'::'eRod_Autonomous_Vehicle_2024'::'Operational Analysis'::'Operational Activities'::'Root Operational Activity'.'Vehicle Command'
                        to component ::> 'eRod_Autonomous_Vehicle_2024 Project'::'eRod_Autonomous_Vehicle_2024'::'Operational Analysis'::'Operational Entities'::'Remote Driver';
                    perform 'eRod_Autonomous_Vehicle_2024 Project'::'eRod_Autonomous_Vehicle_2024'::'Operational Analysis'::'Operational Activities'::'Root Operational Activity'.'Vehicle Command' ; 
                    ref :>> ownedFunctionalAllocation =  ('eRod_Autonomous_Vehicle_2024 Project'::'eRod_Autonomous_Vehicle_2024'::'Operational Analysis'::'Operational Entities'::'Remote Driver'.'eff29269-6858-400b-8174-073907889f74',
                    'eRod_Autonomous_Vehicle_2024 Project'::'eRod_Autonomous_Vehicle_2024'::'Operational Analysis'::'Operational Entities'::'Remote Driver'.'0da12271-3df6-4156-87d8-0d24b47f536f'); 
                }  
            } 
        } 
        package  'System Analysis' {
            @PackageMeta {
                type = "SystemAnalysis";
            } 
            @CapellaID { eid = "cfd9cbdc-3cf7-4fe7-83a9-bc225c001484"; } 
            package  'System Functions' {
                @PackageMeta {
                    type = "SystemFunctionPkg";
                } 
                @CapellaID { eid = "363a27eb-ed3a-40c2-8409-675fa071410d"; } 
                action 'Root System Function' : SystemFunction  { 
                    @CapellaID { eid = "4bdbf9a1-1ae6-4958-b4f2-50791b87df99"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> kind = FunctionKind::FUNCTION; 
                    attribute :>> isMaxInclusive = false; 
                    attribute :>> isMinInclusive = false; 
                    attribute :>> isOrdered = false; 
                    attribute :>> isUnique = false; 
                    action 'Software update' : FunctionalChain  { 
                        @CapellaID { eid = "237f09f8-7013-4082-bbe7-af4f1371952c"; } 
                        attribute :>> kind = FunctionalChainKind::SIMPLE; 
                        ref action '4928f0b0-e0c5-4115-8f37-15955a9cd2fa' = 'eRod_Autonomous_Vehicle_2024 Project'::'eRod_Autonomous_Vehicle_2024'::'System Analysis'::'System Functions'::'Root System Function'.'Report issues'; 
                        connection '5ac3eb77-4a28-4a4a-b364-90843b571dcc' : FunctionalChainInvolvementLink 
                            connect source ::> 'eRod_Autonomous_Vehicle_2024 Project'::'eRod_Autonomous_Vehicle_2024'::'System Analysis'::'System Functions'::'Root System Function'.'Software update'.'4928f0b0-e0c5-4115-8f37-15955a9cd2fa'
                            to  target ::> 'eRod_Autonomous_Vehicle_2024 Project'::'eRod_Autonomous_Vehicle_2024'::'System Analysis'::'System Functions'::'Root System Function'.'Software update'.'82a6e22e-bd2c-4011-baf3-408b1da55775' {

                                ref :>> involved = 'eRod_Autonomous_Vehicle_2024 Project'::'eRod_Autonomous_Vehicle_2024'::'System Analysis'::'System Functions'::'Root System Function'.'25064f56-87cc-4979-8faa-278388d7016e';

                            } 
                        ref action '82a6e22e-bd2c-4011-baf3-408b1da55775' = 'eRod_Autonomous_Vehicle_2024 Project'::'eRod_Autonomous_Vehicle_2024'::'System Analysis'::'System Functions'::'Root System Function'.'Recieve feedback'; 
                        connection 'f650d30d-477f-4cb8-8e57-8d5ccd751ca1' : FunctionalChainInvolvementLink 
                            connect source ::> 'eRod_Autonomous_Vehicle_2024 Project'::'eRod_Autonomous_Vehicle_2024'::'System Analysis'::'System Functions'::'Root System Function'.'Software update'.'82a6e22e-bd2c-4011-baf3-408b1da55775'
                            to  target ::> 'eRod_Autonomous_Vehicle_2024 Project'::'eRod_Autonomous_Vehicle_2024'::'System Analysis'::'System Functions'::'Root System Function'.'Software update'.'3e28eac9-9766-483a-83c8-ffbf8d0b1f60' {

                                ref :>> involved = 'eRod_Autonomous_Vehicle_2024 Project'::'eRod_Autonomous_Vehicle_2024'::'System Analysis'::'System Functions'::'Root System Function'.'c2e16c1d-e749-4725-b483-7bb13e50d93e';

                            } 
                        ref action '3e28eac9-9766-483a-83c8-ffbf8d0b1f60' = 'eRod_Autonomous_Vehicle_2024 Project'::'eRod_Autonomous_Vehicle_2024'::'System Analysis'::'System Functions'::'Root System Function'.'Provide solution'; 
                        connection 'a5a6de20-b8dc-4fe4-95b3-5024131e888e' : FunctionalChainInvolvementLink 
                            connect source ::> 'eRod_Autonomous_Vehicle_2024 Project'::'eRod_Autonomous_Vehicle_2024'::'System Analysis'::'System Functions'::'Root System Function'.'Software update'.'3e28eac9-9766-483a-83c8-ffbf8d0b1f60'
                            to  target ::> 'eRod_Autonomous_Vehicle_2024 Project'::'eRod_Autonomous_Vehicle_2024'::'System Analysis'::'System Functions'::'Root System Function'.'Software update'.'fd920e26-00c7-49e1-8754-5a6e35586734' {

                                ref :>> involved = 'eRod_Autonomous_Vehicle_2024 Project'::'eRod_Autonomous_Vehicle_2024'::'System Analysis'::'System Functions'::'Root System Function'.'e03fd420-1c53-4d50-b06c-f1c1a87d6e3a';

                            } 
                        ref action 'fd920e26-00c7-49e1-8754-5a6e35586734' = 'eRod_Autonomous_Vehicle_2024 Project'::'eRod_Autonomous_Vehicle_2024'::'System Analysis'::'System Functions'::'Root System Function'.'Get Software-update'; 
                        connection '8388783f-377e-420f-bfab-266e5e94cc48' : FunctionalChainInvolvementLink 
                            connect source ::> 'eRod_Autonomous_Vehicle_2024 Project'::'eRod_Autonomous_Vehicle_2024'::'System Analysis'::'System Functions'::'Root System Function'.'Software update'.'fd920e26-00c7-49e1-8754-5a6e35586734'
                            to  target ::> 'eRod_Autonomous_Vehicle_2024 Project'::'eRod_Autonomous_Vehicle_2024'::'System Analysis'::'System Functions'::'Root System Function'.'Software update'.'71bf1850-1157-4490-9d44-12a677b0d782' {

                                ref :>> involved = 'eRod_Autonomous_Vehicle_2024 Project'::'eRod_Autonomous_Vehicle_2024'::'System Analysis'::'System Functions'::'Root System Function'.'abab0827-19f7-442d-b63c-473eea84d95d';

                            } 
                        ref action '71bf1850-1157-4490-9d44-12a677b0d782' = 'eRod_Autonomous_Vehicle_2024 Project'::'eRod_Autonomous_Vehicle_2024'::'System Analysis'::'System Functions'::'Root System Function'.'Software update'; 
                        connection '751400d4-2efd-45b4-a84f-a2bf4774ed91' : FunctionalChainInvolvementLink 
                            connect source ::> 'eRod_Autonomous_Vehicle_2024 Project'::'eRod_Autonomous_Vehicle_2024'::'System Analysis'::'System Functions'::'Root System Function'.'Software update'.'71bf1850-1157-4490-9d44-12a677b0d782'
                            to  target ::> 'eRod_Autonomous_Vehicle_2024 Project'::'eRod_Autonomous_Vehicle_2024'::'System Analysis'::'System Functions'::'Root System Function'.'Software update'.'ea56d07f-cc53-4744-bcde-b5a473679e5b' {

                                ref :>> involved = 'eRod_Autonomous_Vehicle_2024 Project'::'eRod_Autonomous_Vehicle_2024'::'System Analysis'::'System Functions'::'Root System Function'.'f43b7ea7-8fb8-410f-adfa-0521a4349d3f';

                            } 
                        ref action 'ea56d07f-cc53-4744-bcde-b5a473679e5b' = 'eRod_Autonomous_Vehicle_2024 Project'::'eRod_Autonomous_Vehicle_2024'::'System Analysis'::'System Functions'::'Root System Function'.'Control temperature'.'Limit temperature'; 
                        connection '716c766a-6415-46c5-8fcf-ef2234503180' : FunctionalChainInvolvementLink 
                            connect source ::> 'eRod_Autonomous_Vehicle_2024 Project'::'eRod_Autonomous_Vehicle_2024'::'System Analysis'::'System Functions'::'Root System Function'.'Software update'.'ea56d07f-cc53-4744-bcde-b5a473679e5b'
                            to  target ::> 'eRod_Autonomous_Vehicle_2024 Project'::'eRod_Autonomous_Vehicle_2024'::'System Analysis'::'System Functions'::'Root System Function'.'Software update'.'93745d92-c98a-4e4a-82db-ea8b13699d6b' {

                                ref :>> involved = 'eRod_Autonomous_Vehicle_2024 Project'::'eRod_Autonomous_Vehicle_2024'::'System Analysis'::'System Functions'::'Root System Function'.'Control temperature'.'18057854-deb7-4fe3-b819-59ae67e7b705';

                            } 
                        ref action '93745d92-c98a-4e4a-82db-ea8b13699d6b' = 'eRod_Autonomous_Vehicle_2024 Project'::'eRod_Autonomous_Vehicle_2024'::'System Analysis'::'System Functions'::'Root System Function'.'Control temperature'.'Limit power'; 
                        connection '76e35ac5-3f93-4792-9280-7ac7e80920c6' : FunctionalChainInvolvementLink 
                            connect source ::> 'eRod_Autonomous_Vehicle_2024 Project'::'eRod_Autonomous_Vehicle_2024'::'System Analysis'::'System Functions'::'Root System Function'.'Software update'.'93745d92-c98a-4e4a-82db-ea8b13699d6b'
                            to  target ::> 'eRod_Autonomous_Vehicle_2024 Project'::'eRod_Autonomous_Vehicle_2024'::'System Analysis'::'System Functions'::'Root System Function'.'Software update'.'66d08964-5664-4406-99dd-67296a2236df' {

                                ref :>> involved = 'eRod_Autonomous_Vehicle_2024 Project'::'eRod_Autonomous_Vehicle_2024'::'System Analysis'::'System Functions'::'Root System Function'.'8b48666c-343c-4dc4-8cb1-6710f32ac69d';

                            } 
                        ref action '66d08964-5664-4406-99dd-67296a2236df' = 'eRod_Autonomous_Vehicle_2024 Project'::'eRod_Autonomous_Vehicle_2024'::'System Analysis'::'System Functions'::'Root System Function'.'Sporty drive'; 
                        connection 'ff4c9341-9c64-4687-adc7-03ddec08060a' : FunctionalChainInvolvementLink 
                            connect source ::> 'eRod_Autonomous_Vehicle_2024 Project'::'eRod_Autonomous_Vehicle_2024'::'System Analysis'::'System Functions'::'Root System Function'.'Software update'.'71bf1850-1157-4490-9d44-12a677b0d782'
                            to  target ::> 'eRod_Autonomous_Vehicle_2024 Project'::'eRod_Autonomous_Vehicle_2024'::'System Analysis'::'System Functions'::'Root System Function'.'Software update'.'66d08964-5664-4406-99dd-67296a2236df' {

                                ref :>> involved = 'eRod_Autonomous_Vehicle_2024 Project'::'eRod_Autonomous_Vehicle_2024'::'System Analysis'::'System Functions'::'Root System Function'.'5554cc7d-cd17-43bf-ae7b-14819bfb763e';

                            } 
                        ref action 'dd0897ce-76d2-4892-9975-094b59c686de' = 'eRod_Autonomous_Vehicle_2024 Project'::'eRod_Autonomous_Vehicle_2024'::'System Analysis'::'System Functions'::'Root System Function'.'Transfer Energy'.'Acquire Energy'; 
                        connection '531a1cc7-34ad-493a-b769-5e80255b7fce' : FunctionalChainInvolvementLink 
                            connect source ::> 'eRod_Autonomous_Vehicle_2024 Project'::'eRod_Autonomous_Vehicle_2024'::'System Analysis'::'System Functions'::'Root System Function'.'Software update'.'dd0897ce-76d2-4892-9975-094b59c686de'
                            to  target ::> 'eRod_Autonomous_Vehicle_2024 Project'::'eRod_Autonomous_Vehicle_2024'::'System Analysis'::'System Functions'::'Root System Function'.'Software update'.'a65abff3-a7cd-4a6a-9223-5f91f260ccc1' {

                                ref :>> involved = 'eRod_Autonomous_Vehicle_2024 Project'::'eRod_Autonomous_Vehicle_2024'::'System Analysis'::'System Functions'::'Root System Function'.'Transfer Energy'.'cfeffdb3-21f9-4dba-9ed3-1a80cfd0de71';

                            } 
                        ref action 'a65abff3-a7cd-4a6a-9223-5f91f260ccc1' = 'eRod_Autonomous_Vehicle_2024 Project'::'eRod_Autonomous_Vehicle_2024'::'System Analysis'::'System Functions'::'Root System Function'.'Transfer Energy'.'Tranfer electrical energy into mechanical energy'; 
                        connection '25095695-6383-4623-975b-398a124c6f3c' : FunctionalChainInvolvementLink 
                            connect source ::> 'eRod_Autonomous_Vehicle_2024 Project'::'eRod_Autonomous_Vehicle_2024'::'System Analysis'::'System Functions'::'Root System Function'.'Software update'.'a65abff3-a7cd-4a6a-9223-5f91f260ccc1'
                            to  target ::> 'eRod_Autonomous_Vehicle_2024 Project'::'eRod_Autonomous_Vehicle_2024'::'System Analysis'::'System Functions'::'Root System Function'.'Software update'.'95fc29aa-a410-453b-b038-6fb4ba51442a' {

                                ref :>> involved = 'eRod_Autonomous_Vehicle_2024 Project'::'eRod_Autonomous_Vehicle_2024'::'System Analysis'::'System Functions'::'Root System Function'.'Transfer Energy'.'9e076827-cd80-4f42-9899-127265c6a576';

                            } 
                        ref action '95fc29aa-a410-453b-b038-6fb4ba51442a' = 'eRod_Autonomous_Vehicle_2024 Project'::'eRod_Autonomous_Vehicle_2024'::'System Analysis'::'System Functions'::'Root System Function'.'Transfer Energy'.'Generate heat'; 
                        connection '7461a777-f61d-4f77-8b6e-98c2b8383ddd' : FunctionalChainInvolvementLink 
                            connect source ::> 'eRod_Autonomous_Vehicle_2024 Project'::'eRod_Autonomous_Vehicle_2024'::'System Analysis'::'System Functions'::'Root System Function'.'Software update'.'95fc29aa-a410-453b-b038-6fb4ba51442a'
                            to  target ::> 'eRod_Autonomous_Vehicle_2024 Project'::'eRod_Autonomous_Vehicle_2024'::'System Analysis'::'System Functions'::'Root System Function'.'Software update'.'ae032d4c-eb23-43d1-9250-522dddd26155' {

                                ref :>> involved = 'eRod_Autonomous_Vehicle_2024 Project'::'eRod_Autonomous_Vehicle_2024'::'System Analysis'::'System Functions'::'Root System Function'.'fee0d319-e733-453f-9146-6f29048c6d35';

                            } 
                        ref action 'ae032d4c-eb23-43d1-9250-522dddd26155' = 'eRod_Autonomous_Vehicle_2024 Project'::'eRod_Autonomous_Vehicle_2024'::'System Analysis'::'System Functions'::'Root System Function'.'Motor protect'.'Monitor temperature'; 
                        connection 'b27003a8-ae7e-4f6e-b9d8-71ffd5e6084f' : FunctionalChainInvolvementLink 
                            connect source ::> 'eRod_Autonomous_Vehicle_2024 Project'::'eRod_Autonomous_Vehicle_2024'::'System Analysis'::'System Functions'::'Root System Function'.'Software update'.'a65abff3-a7cd-4a6a-9223-5f91f260ccc1'
                            to  target ::> 'eRod_Autonomous_Vehicle_2024 Project'::'eRod_Autonomous_Vehicle_2024'::'System Analysis'::'System Functions'::'Root System Function'.'Software update'.'aecd57c6-41cb-4d86-9062-f8e229fb79a5' {

                                ref :>> involved = 'eRod_Autonomous_Vehicle_2024 Project'::'eRod_Autonomous_Vehicle_2024'::'System Analysis'::'System Functions'::'Root System Function'.'Transfer Energy'.'b2a28595-ce9f-44d9-854e-a10d0aa34bd2';

                            } 
                        ref action 'aecd57c6-41cb-4d86-9062-f8e229fb79a5' = 'eRod_Autonomous_Vehicle_2024 Project'::'eRod_Autonomous_Vehicle_2024'::'System Analysis'::'System Functions'::'Root System Function'.'Transfer Energy'.'generate power'; 
                        connection 'a5d7135f-77dd-4f4f-89d7-cc627f62a7e3' : FunctionalChainInvolvementLink 
                            connect source ::> 'eRod_Autonomous_Vehicle_2024 Project'::'eRod_Autonomous_Vehicle_2024'::'System Analysis'::'System Functions'::'Root System Function'.'Software update'.'aecd57c6-41cb-4d86-9062-f8e229fb79a5'
                            to  target ::> 'eRod_Autonomous_Vehicle_2024 Project'::'eRod_Autonomous_Vehicle_2024'::'System Analysis'::'System Functions'::'Root System Function'.'Software update'.'93745d92-c98a-4e4a-82db-ea8b13699d6b' {

                                ref :>> involved = 'eRod_Autonomous_Vehicle_2024 Project'::'eRod_Autonomous_Vehicle_2024'::'System Analysis'::'System Functions'::'Root System Function'.'41db3cad-802d-4343-b3aa-4b18c5dd96d5';

                            } 
                         
                    }  
                    action 'Overheating' : FunctionalChain  { 
                        @CapellaID { eid = "3eb42063-e676-49c5-afd7-a7b9fa5fcaa9"; } 
                        attribute :>> kind = FunctionalChainKind::SIMPLE; 
                        ref action '456178c7-32e8-4968-b57e-798f944a2aa3' = 'eRod_Autonomous_Vehicle_2024 Project'::'eRod_Autonomous_Vehicle_2024'::'System Analysis'::'System Functions'::'Root System Function'.'Drive on a race track'; 
                        connection '46a2773b-8c5a-43cc-91b7-0411e3fe11c7' : FunctionalChainInvolvementLink 
                            connect source ::> 'eRod_Autonomous_Vehicle_2024 Project'::'eRod_Autonomous_Vehicle_2024'::'System Analysis'::'System Functions'::'Root System Function'.'Overheating'.'456178c7-32e8-4968-b57e-798f944a2aa3'
                            to  target ::> 'eRod_Autonomous_Vehicle_2024 Project'::'eRod_Autonomous_Vehicle_2024'::'System Analysis'::'System Functions'::'Root System Function'.'Overheating'.'a3c54958-54dc-487a-be75-30f118c0ab44' {

                                ref :>> involved = 'eRod_Autonomous_Vehicle_2024 Project'::'eRod_Autonomous_Vehicle_2024'::'System Analysis'::'System Functions'::'Root System Function'.'21737cb1-a533-4e0e-b423-e8d1c433d866';

                            } 
                        ref action 'a3c54958-54dc-487a-be75-30f118c0ab44' = 'eRod_Autonomous_Vehicle_2024 Project'::'eRod_Autonomous_Vehicle_2024'::'System Analysis'::'System Functions'::'Root System Function'.'Sporty drive'; 
                        connection 'acf49093-5782-42c8-9299-66cbe9b890b9' : FunctionalChainInvolvementLink 
                            connect source ::> 'eRod_Autonomous_Vehicle_2024 Project'::'eRod_Autonomous_Vehicle_2024'::'System Analysis'::'System Functions'::'Root System Function'.'Overheating'.'a3c54958-54dc-487a-be75-30f118c0ab44'
                            to  target ::> 'eRod_Autonomous_Vehicle_2024 Project'::'eRod_Autonomous_Vehicle_2024'::'System Analysis'::'System Functions'::'Root System Function'.'Overheating'.'bfedb759-6f82-4a98-8b5d-0c2b4a932472' {

                                ref :>> involved = 'eRod_Autonomous_Vehicle_2024 Project'::'eRod_Autonomous_Vehicle_2024'::'System Analysis'::'System Functions'::'Root System Function'.'c8739b1d-878b-4b72-851e-26839aeec754';

                            } 
                        ref action 'bfedb759-6f82-4a98-8b5d-0c2b4a932472' = 'eRod_Autonomous_Vehicle_2024 Project'::'eRod_Autonomous_Vehicle_2024'::'System Analysis'::'System Functions'::'Root System Function'.'Transfer Energy'.'Acquire Energy'; 
                        connection '8ee98f43-e380-4b57-aee0-48ba81f32201' : FunctionalChainInvolvementLink 
                            connect source ::> 'eRod_Autonomous_Vehicle_2024 Project'::'eRod_Autonomous_Vehicle_2024'::'System Analysis'::'System Functions'::'Root System Function'.'Overheating'.'bfedb759-6f82-4a98-8b5d-0c2b4a932472'
                            to  target ::> 'eRod_Autonomous_Vehicle_2024 Project'::'eRod_Autonomous_Vehicle_2024'::'System Analysis'::'System Functions'::'Root System Function'.'Overheating'.'085745c2-641d-49ca-807b-c7b5c49456bf' {

                                ref :>> involved = 'eRod_Autonomous_Vehicle_2024 Project'::'eRod_Autonomous_Vehicle_2024'::'System Analysis'::'System Functions'::'Root System Function'.'Transfer Energy'.'cfeffdb3-21f9-4dba-9ed3-1a80cfd0de71';

                            } 
                        ref action '085745c2-641d-49ca-807b-c7b5c49456bf' = 'eRod_Autonomous_Vehicle_2024 Project'::'eRod_Autonomous_Vehicle_2024'::'System Analysis'::'System Functions'::'Root System Function'.'Transfer Energy'.'Tranfer electrical energy into mechanical energy'; 
                        connection '0594ac35-bbac-49b5-b955-c8ceb7e949df' : FunctionalChainInvolvementLink 
                            connect source ::> 'eRod_Autonomous_Vehicle_2024 Project'::'eRod_Autonomous_Vehicle_2024'::'System Analysis'::'System Functions'::'Root System Function'.'Overheating'.'085745c2-641d-49ca-807b-c7b5c49456bf'
                            to  target ::> 'eRod_Autonomous_Vehicle_2024 Project'::'eRod_Autonomous_Vehicle_2024'::'System Analysis'::'System Functions'::'Root System Function'.'Overheating'.'4a97221c-3258-4c57-9c8c-124fe9c990f1' {

                                ref :>> involved = 'eRod_Autonomous_Vehicle_2024 Project'::'eRod_Autonomous_Vehicle_2024'::'System Analysis'::'System Functions'::'Root System Function'.'Transfer Energy'.'b2a28595-ce9f-44d9-854e-a10d0aa34bd2';

                            } 
                        ref action '4a97221c-3258-4c57-9c8c-124fe9c990f1' = 'eRod_Autonomous_Vehicle_2024 Project'::'eRod_Autonomous_Vehicle_2024'::'System Analysis'::'System Functions'::'Root System Function'.'Transfer Energy'.'generate power'; 
                        connection '15e15785-c8e6-4a8b-99c4-f8789bd7fed1' : FunctionalChainInvolvementLink 
                            connect source ::> 'eRod_Autonomous_Vehicle_2024 Project'::'eRod_Autonomous_Vehicle_2024'::'System Analysis'::'System Functions'::'Root System Function'.'Overheating'.'085745c2-641d-49ca-807b-c7b5c49456bf'
                            to  target ::> 'eRod_Autonomous_Vehicle_2024 Project'::'eRod_Autonomous_Vehicle_2024'::'System Analysis'::'System Functions'::'Root System Function'.'Overheating'.'b6664d5a-70a3-41ff-a88d-58a9b34fcd85' {

                                ref :>> involved = 'eRod_Autonomous_Vehicle_2024 Project'::'eRod_Autonomous_Vehicle_2024'::'System Analysis'::'System Functions'::'Root System Function'.'Transfer Energy'.'9e076827-cd80-4f42-9899-127265c6a576';

                            } 
                        ref action 'b6664d5a-70a3-41ff-a88d-58a9b34fcd85' = 'eRod_Autonomous_Vehicle_2024 Project'::'eRod_Autonomous_Vehicle_2024'::'System Analysis'::'System Functions'::'Root System Function'.'Transfer Energy'.'Generate heat'; 
                        connection 'e67f6193-3b98-4156-bae0-5de101e50f85' : FunctionalChainInvolvementLink 
                            connect source ::> 'eRod_Autonomous_Vehicle_2024 Project'::'eRod_Autonomous_Vehicle_2024'::'System Analysis'::'System Functions'::'Root System Function'.'Overheating'.'b6664d5a-70a3-41ff-a88d-58a9b34fcd85'
                            to  target ::> 'eRod_Autonomous_Vehicle_2024 Project'::'eRod_Autonomous_Vehicle_2024'::'System Analysis'::'System Functions'::'Root System Function'.'Overheating'.'9867fd52-246a-46b6-bbc1-33b2a5684ea9' {

                                ref :>> involved = 'eRod_Autonomous_Vehicle_2024 Project'::'eRod_Autonomous_Vehicle_2024'::'System Analysis'::'System Functions'::'Root System Function'.'fee0d319-e733-453f-9146-6f29048c6d35';

                            } 
                        ref action '9867fd52-246a-46b6-bbc1-33b2a5684ea9' = 'eRod_Autonomous_Vehicle_2024 Project'::'eRod_Autonomous_Vehicle_2024'::'System Analysis'::'System Functions'::'Root System Function'.'Motor protect'.'Monitor temperature'; 
                        connection '44636acb-010e-4d3d-b70a-86896b8d6c73' : FunctionalChainInvolvementLink 
                            connect source ::> 'eRod_Autonomous_Vehicle_2024 Project'::'eRod_Autonomous_Vehicle_2024'::'System Analysis'::'System Functions'::'Root System Function'.'Overheating'.'9867fd52-246a-46b6-bbc1-33b2a5684ea9'
                            to  target ::> 'eRod_Autonomous_Vehicle_2024 Project'::'eRod_Autonomous_Vehicle_2024'::'System Analysis'::'System Functions'::'Root System Function'.'Overheating'.'e69d0432-1e04-431f-89d4-59f49600eb31' {

                                ref :>> involved = 'eRod_Autonomous_Vehicle_2024 Project'::'eRod_Autonomous_Vehicle_2024'::'System Analysis'::'System Functions'::'Root System Function'.'Motor protect'.'2931413b-f2c8-4514-a67c-7126167c0bae';

                            } 
                        ref action 'e69d0432-1e04-431f-89d4-59f49600eb31' = 'eRod_Autonomous_Vehicle_2024 Project'::'eRod_Autonomous_Vehicle_2024'::'System Analysis'::'System Functions'::'Root System Function'.'Motor protect'.'Detect temperature limit'; 
                        connection 'eeaeb109-f0fa-4b90-a27d-2a359b8d91c4' : FunctionalChainInvolvementLink 
                            connect source ::> 'eRod_Autonomous_Vehicle_2024 Project'::'eRod_Autonomous_Vehicle_2024'::'System Analysis'::'System Functions'::'Root System Function'.'Overheating'.'4a97221c-3258-4c57-9c8c-124fe9c990f1'
                            to  target ::> 'eRod_Autonomous_Vehicle_2024 Project'::'eRod_Autonomous_Vehicle_2024'::'System Analysis'::'System Functions'::'Root System Function'.'Overheating'.'9c8b95cc-4fd8-45d1-bd31-ca4117b0f432' {

                                ref :>> involved = 'eRod_Autonomous_Vehicle_2024 Project'::'eRod_Autonomous_Vehicle_2024'::'System Analysis'::'System Functions'::'Root System Function'.'86fe5cc7-469e-499d-8dfe-c38fd2504e64';

                            } 
                        ref action '9c8b95cc-4fd8-45d1-bd31-ca4117b0f432' = 'eRod_Autonomous_Vehicle_2024 Project'::'eRod_Autonomous_Vehicle_2024'::'System Analysis'::'System Functions'::'Root System Function'.'Motor protect'.'Reduce power'; 
                        connection '1e290172-70ae-412b-8894-30d001036a17' : FunctionalChainInvolvementLink 
                            connect source ::> 'eRod_Autonomous_Vehicle_2024 Project'::'eRod_Autonomous_Vehicle_2024'::'System Analysis'::'System Functions'::'Root System Function'.'Overheating'.'9c8b95cc-4fd8-45d1-bd31-ca4117b0f432'
                            to  target ::> 'eRod_Autonomous_Vehicle_2024 Project'::'eRod_Autonomous_Vehicle_2024'::'System Analysis'::'System Functions'::'Root System Function'.'Overheating'.'60223bd0-f174-405c-ade6-24c4e4cd34ef' {

                                ref :>> involved = 'eRod_Autonomous_Vehicle_2024 Project'::'eRod_Autonomous_Vehicle_2024'::'System Analysis'::'System Functions'::'Root System Function'.'fe887ba1-b3ff-4c0e-8f2d-2e4acb6302f6';

                            } 
                        ref action '60223bd0-f174-405c-ade6-24c4e4cd34ef' = 'eRod_Autonomous_Vehicle_2024 Project'::'eRod_Autonomous_Vehicle_2024'::'System Analysis'::'System Functions'::'Root System Function'.'Deaccelerate'; 
                        connection '274a2593-46be-484b-a1aa-325297b0fcd0' : FunctionalChainInvolvementLink 
                            connect source ::> 'eRod_Autonomous_Vehicle_2024 Project'::'eRod_Autonomous_Vehicle_2024'::'System Analysis'::'System Functions'::'Root System Function'.'Overheating'.'60223bd0-f174-405c-ade6-24c4e4cd34ef'
                            to  target ::> 'eRod_Autonomous_Vehicle_2024 Project'::'eRod_Autonomous_Vehicle_2024'::'System Analysis'::'System Functions'::'Root System Function'.'Overheating'.'5abb58fb-88be-47f1-a7be-7d8ad2d1b628' {

                                ref :>> involved = 'eRod_Autonomous_Vehicle_2024 Project'::'eRod_Autonomous_Vehicle_2024'::'System Analysis'::'System Functions'::'Root System Function'.'bbe4b2d5-09e2-426f-9c95-3c2f0942e5e2';

                            } 
                        ref action '5abb58fb-88be-47f1-a7be-7d8ad2d1b628' = 'eRod_Autonomous_Vehicle_2024 Project'::'eRod_Autonomous_Vehicle_2024'::'System Analysis'::'System Functions'::'Root System Function'.'Stop'; 
                        connection 'be5d84a1-dd70-4eb6-9bfe-da255e965a81' : FunctionalChainInvolvementLink 
                            connect source ::> 'eRod_Autonomous_Vehicle_2024 Project'::'eRod_Autonomous_Vehicle_2024'::'System Analysis'::'System Functions'::'Root System Function'.'Overheating'.'5abb58fb-88be-47f1-a7be-7d8ad2d1b628'
                            to  target ::> 'eRod_Autonomous_Vehicle_2024 Project'::'eRod_Autonomous_Vehicle_2024'::'System Analysis'::'System Functions'::'Root System Function'.'Overheating'.'7a0c025a-60ae-4efe-83a6-1ca143fe0532' {

                                ref :>> involved = 'eRod_Autonomous_Vehicle_2024 Project'::'eRod_Autonomous_Vehicle_2024'::'System Analysis'::'System Functions'::'Root System Function'.'09928616-6ea6-40cc-82a0-fb0aaa5ff578';

                            } 
                        ref action '7a0c025a-60ae-4efe-83a6-1ca143fe0532' = 'eRod_Autonomous_Vehicle_2024 Project'::'eRod_Autonomous_Vehicle_2024'::'System Analysis'::'System Functions'::'Root System Function'.'Car racing experience absorbed'; 
                        connection '69ae4739-f7c2-4dec-8d30-fb057715376e' : FunctionalChainInvolvementLink 
                            connect source ::> 'eRod_Autonomous_Vehicle_2024 Project'::'eRod_Autonomous_Vehicle_2024'::'System Analysis'::'System Functions'::'Root System Function'.'Overheating'.'e69d0432-1e04-431f-89d4-59f49600eb31'
                            to  target ::> 'eRod_Autonomous_Vehicle_2024 Project'::'eRod_Autonomous_Vehicle_2024'::'System Analysis'::'System Functions'::'Root System Function'.'Overheating'.'6fb609ce-f353-41e0-af99-afde324f66ba' {

                                ref :>> involved = 'eRod_Autonomous_Vehicle_2024 Project'::'eRod_Autonomous_Vehicle_2024'::'System Analysis'::'System Functions'::'Root System Function'.'d3505a26-4e29-4af9-8608-c1023a575945';

                            } 
                        ref action '6fb609ce-f353-41e0-af99-afde324f66ba' = 'eRod_Autonomous_Vehicle_2024 Project'::'eRod_Autonomous_Vehicle_2024'::'System Analysis'::'System Functions'::'Root System Function'.'Motor overheating warning '; 
                        connection '53dd784f-5ba7-4a06-b9bf-3004c6ac96d2' : FunctionalChainInvolvementLink 
                            connect source ::> 'eRod_Autonomous_Vehicle_2024 Project'::'eRod_Autonomous_Vehicle_2024'::'System Analysis'::'System Functions'::'Root System Function'.'Overheating'.'6fb609ce-f353-41e0-af99-afde324f66ba'
                            to  target ::> 'eRod_Autonomous_Vehicle_2024 Project'::'eRod_Autonomous_Vehicle_2024'::'System Analysis'::'System Functions'::'Root System Function'.'Overheating'.'d3196399-2717-4b8a-b21e-8d293629f9b7' {

                                ref :>> involved = 'eRod_Autonomous_Vehicle_2024 Project'::'eRod_Autonomous_Vehicle_2024'::'System Analysis'::'System Functions'::'Root System Function'.'cdf6cd1f-fbf7-4fc5-a568-e76b603a21b9';

                            } 
                        ref action 'd3196399-2717-4b8a-b21e-8d293629f9b7' = 'eRod_Autonomous_Vehicle_2024 Project'::'eRod_Autonomous_Vehicle_2024'::'System Analysis'::'System Functions'::'Root System Function'.'Get informed with issues'; 
                        connection '1adfe77a-97f6-469d-a1a0-d65a530b08e0' : FunctionalChainInvolvementLink 
                            connect source ::> 'eRod_Autonomous_Vehicle_2024 Project'::'eRod_Autonomous_Vehicle_2024'::'System Analysis'::'System Functions'::'Root System Function'.'Overheating'.'d3196399-2717-4b8a-b21e-8d293629f9b7'
                            to  target ::> 'eRod_Autonomous_Vehicle_2024 Project'::'eRod_Autonomous_Vehicle_2024'::'System Analysis'::'System Functions'::'Root System Function'.'Overheating'.'47d6928b-9589-44ec-b085-5117071c8e0a' {

                                ref :>> involved = 'eRod_Autonomous_Vehicle_2024 Project'::'eRod_Autonomous_Vehicle_2024'::'System Analysis'::'System Functions'::'Root System Function'.'c698f103-54ac-491b-a6f4-d764baf0383c';

                            } 
                        ref action '47d6928b-9589-44ec-b085-5117071c8e0a' = 'eRod_Autonomous_Vehicle_2024 Project'::'eRod_Autonomous_Vehicle_2024'::'System Analysis'::'System Functions'::'Root System Function'.'Report issues'; 
                         
                    }  
                    action 'Automatic Emergency Braking (AEB)' : FunctionalChain  { 
                        @CapellaID { eid = "1b6880a3-2c93-4ad5-b240-301765934dfa"; } 
                        attribute :>> kind = FunctionalChainKind::SIMPLE; 
                        connection '598de403-1869-4560-bb1e-10f070149942' : FunctionalChainInvolvementLink 
                            connect source ::> 'eRod_Autonomous_Vehicle_2024 Project'::'eRod_Autonomous_Vehicle_2024'::'System Analysis'::'System Functions'::'Root System Function'.'Automatic Emergency Braking (AEB)'.'f5222cf9-de73-43fe-935f-6c5b04ecfd2f'
                            to  target ::> 'eRod_Autonomous_Vehicle_2024 Project'::'eRod_Autonomous_Vehicle_2024'::'System Analysis'::'System Functions'::'Root System Function'.'Automatic Emergency Braking (AEB)'.'63c1ae19-c7c4-4af7-8263-4431abec8ca5' {

                                ref :>> involved = 'eRod_Autonomous_Vehicle_2024 Project'::'eRod_Autonomous_Vehicle_2024'::'System Analysis'::'System Functions'::'Root System Function'.'851fafb3-489b-4ac0-93b3-d5bead2317f5';

                            } 
                        ref action '63c1ae19-c7c4-4af7-8263-4431abec8ca5' = 'eRod_Autonomous_Vehicle_2024 Project'::'eRod_Autonomous_Vehicle_2024'::'System Analysis'::'System Functions'::'Root System Function'.'Locate targets'; 
                        ref action 'f5222cf9-de73-43fe-935f-6c5b04ecfd2f' = 'eRod_Autonomous_Vehicle_2024 Project'::'eRod_Autonomous_Vehicle_2024'::'System Analysis'::'System Functions'::'Root System Function'.'Provide object location'; 
                        connection '617c8879-22a3-4e64-ba10-6351c14aa451' : FunctionalChainInvolvementLink 
                            connect source ::> 'eRod_Autonomous_Vehicle_2024 Project'::'eRod_Autonomous_Vehicle_2024'::'System Analysis'::'System Functions'::'Root System Function'.'Automatic Emergency Braking (AEB)'.'63c1ae19-c7c4-4af7-8263-4431abec8ca5'
                            to  target ::> 'eRod_Autonomous_Vehicle_2024 Project'::'eRod_Autonomous_Vehicle_2024'::'System Analysis'::'System Functions'::'Root System Function'.'Automatic Emergency Braking (AEB)'.'8b477810-305f-475f-ab69-8d27d858a32a' {

                                ref :>> involved = 'eRod_Autonomous_Vehicle_2024 Project'::'eRod_Autonomous_Vehicle_2024'::'System Analysis'::'System Functions'::'Root System Function'.'22434d92-754d-43b3-bd5d-87cd48be77b1';

                            } 
                        ref action '8b477810-305f-475f-ab69-8d27d858a32a' = 'eRod_Autonomous_Vehicle_2024 Project'::'eRod_Autonomous_Vehicle_2024'::'System Analysis'::'System Functions'::'Root System Function'.'Avoid collision'; 
                        connection 'c321b48c-3136-4916-ace3-4c864a3b6917' : FunctionalChainInvolvementLink 
                            connect source ::> 'eRod_Autonomous_Vehicle_2024 Project'::'eRod_Autonomous_Vehicle_2024'::'System Analysis'::'System Functions'::'Root System Function'.'Automatic Emergency Braking (AEB)'.'8b477810-305f-475f-ab69-8d27d858a32a'
                            to  target ::> 'eRod_Autonomous_Vehicle_2024 Project'::'eRod_Autonomous_Vehicle_2024'::'System Analysis'::'System Functions'::'Root System Function'.'Automatic Emergency Braking (AEB)'.'ca392b6b-8c7d-40ca-ba45-7e728136ecf3' {

                                ref :>> involved = 'eRod_Autonomous_Vehicle_2024 Project'::'eRod_Autonomous_Vehicle_2024'::'System Analysis'::'System Functions'::'Root System Function'.'21c5ea50-56cf-4e17-b90e-c25092178078';

                            } 
                        ref action 'ca392b6b-8c7d-40ca-ba45-7e728136ecf3' = 'eRod_Autonomous_Vehicle_2024 Project'::'eRod_Autonomous_Vehicle_2024'::'System Analysis'::'System Functions'::'Root System Function'.'Control braking'; 
                    }  
                    action 'Forward Collision Warning (FCW)' : FunctionalChain  { 
                        @CapellaID { eid = "418d597b-afc0-4cdf-8967-101418c9e989"; } 
                        attribute :>> kind = FunctionalChainKind::SIMPLE; 
                        connection '10185165-691f-4170-baf7-a3434f83da7b' : FunctionalChainInvolvementLink 
                            connect source ::> 'eRod_Autonomous_Vehicle_2024 Project'::'eRod_Autonomous_Vehicle_2024'::'System Analysis'::'System Functions'::'Root System Function'.'Forward Collision Warning (FCW)'.'069bf62c-555a-474f-ba12-38f898472b9e'
                            to  target ::> 'eRod_Autonomous_Vehicle_2024 Project'::'eRod_Autonomous_Vehicle_2024'::'System Analysis'::'System Functions'::'Root System Function'.'Forward Collision Warning (FCW)'.'a5c0827e-9390-4c39-8ee7-e964e393a7ef' {

                                ref :>> involved = 'eRod_Autonomous_Vehicle_2024 Project'::'eRod_Autonomous_Vehicle_2024'::'System Analysis'::'System Functions'::'Root System Function'.'dc48f799-dcc2-4510-ad65-155854d64eeb';

                            } 
                        ref action 'a5c0827e-9390-4c39-8ee7-e964e393a7ef' = 'eRod_Autonomous_Vehicle_2024 Project'::'eRod_Autonomous_Vehicle_2024'::'System Analysis'::'System Functions'::'Root System Function'.'Provide vehicle status'; 
                        ref action '069bf62c-555a-474f-ba12-38f898472b9e' = 'eRod_Autonomous_Vehicle_2024 Project'::'eRod_Autonomous_Vehicle_2024'::'System Analysis'::'System Functions'::'Root System Function'.'Avoid collision'; 
                        connection '2102e49a-fc8e-4895-9283-06a493e6f1f6' : FunctionalChainInvolvementLink 
                            connect source ::> 'eRod_Autonomous_Vehicle_2024 Project'::'eRod_Autonomous_Vehicle_2024'::'System Analysis'::'System Functions'::'Root System Function'.'Forward Collision Warning (FCW)'.'a5c0827e-9390-4c39-8ee7-e964e393a7ef'
                            to  target ::> 'eRod_Autonomous_Vehicle_2024 Project'::'eRod_Autonomous_Vehicle_2024'::'System Analysis'::'System Functions'::'Root System Function'.'Forward Collision Warning (FCW)'.'4ede0ed8-cbb9-412d-9954-1e855c2d427b' {

                                ref :>> involved = 'eRod_Autonomous_Vehicle_2024 Project'::'eRod_Autonomous_Vehicle_2024'::'System Analysis'::'System Functions'::'Root System Function'.'d115699f-c1d1-40f3-aa77-65a4aa859c71';

                            } 
                        ref action '4ede0ed8-cbb9-412d-9954-1e855c2d427b' = 'eRod_Autonomous_Vehicle_2024 Project'::'eRod_Autonomous_Vehicle_2024'::'System Analysis'::'System Functions'::'Root System Function'.'Observe status'; 
                    }  
                    action 'Adaptive Cruise Control (ACC)' : FunctionalChain  { 
                        @CapellaID { eid = "15a7117a-c489-4c0a-8494-f9b819a90ab9"; } 
                        attribute :>> kind = FunctionalChainKind::SIMPLE; 
                        connection 'bb52d76b-27db-4ea7-ba97-407566bf6a47' : FunctionalChainInvolvementLink 
                            connect source ::> 'eRod_Autonomous_Vehicle_2024 Project'::'eRod_Autonomous_Vehicle_2024'::'System Analysis'::'System Functions'::'Root System Function'.'Adaptive Cruise Control (ACC)'.'947c1529-2c48-4fb2-b14b-1d3e2c8e45d4'
                            to  target ::> 'eRod_Autonomous_Vehicle_2024 Project'::'eRod_Autonomous_Vehicle_2024'::'System Analysis'::'System Functions'::'Root System Function'.'Adaptive Cruise Control (ACC)'.'7822bc46-8afb-46ec-92df-f20514412b82' {

                                ref :>> involved = 'eRod_Autonomous_Vehicle_2024 Project'::'eRod_Autonomous_Vehicle_2024'::'System Analysis'::'System Functions'::'Root System Function'.'2d1c2035-5524-4691-ae89-77dccea3a761';

                            } 
                        ref action '7822bc46-8afb-46ec-92df-f20514412b82' = 'eRod_Autonomous_Vehicle_2024 Project'::'eRod_Autonomous_Vehicle_2024'::'System Analysis'::'System Functions'::'Root System Function'.'Maintain distance'; 
                        ref action '947c1529-2c48-4fb2-b14b-1d3e2c8e45d4' = 'eRod_Autonomous_Vehicle_2024 Project'::'eRod_Autonomous_Vehicle_2024'::'System Analysis'::'System Functions'::'Root System Function'.'Locate targets'; 
                        connection '182feddf-ea07-4274-82d4-a4f75008308c' : FunctionalChainInvolvementLink 
                            connect source ::> 'eRod_Autonomous_Vehicle_2024 Project'::'eRod_Autonomous_Vehicle_2024'::'System Analysis'::'System Functions'::'Root System Function'.'Adaptive Cruise Control (ACC)'.'7822bc46-8afb-46ec-92df-f20514412b82'
                            to  target ::> 'eRod_Autonomous_Vehicle_2024 Project'::'eRod_Autonomous_Vehicle_2024'::'System Analysis'::'System Functions'::'Root System Function'.'Adaptive Cruise Control (ACC)'.'93f3f338-ad62-4e5c-8939-30bfc1c8c6ac' {

                                ref :>> involved = 'eRod_Autonomous_Vehicle_2024 Project'::'eRod_Autonomous_Vehicle_2024'::'System Analysis'::'System Functions'::'Root System Function'.'4b235453-ef29-4b1b-9828-40efa8737c46';

                            } 
                        ref action '93f3f338-ad62-4e5c-8939-30bfc1c8c6ac' = 'eRod_Autonomous_Vehicle_2024 Project'::'eRod_Autonomous_Vehicle_2024'::'System Analysis'::'System Functions'::'Root System Function'.'Control braking'; 
                        ref action '500d22c2-d370-4952-a64e-c040a85f2de9' = 'eRod_Autonomous_Vehicle_2024 Project'::'eRod_Autonomous_Vehicle_2024'::'System Analysis'::'System Functions'::'Root System Function'.'Maintain speed'; 
                        connection 'e88f198f-d6f3-47e7-9f5b-46fdb9fd28cb' : FunctionalChainInvolvementLink 
                            connect source ::> 'eRod_Autonomous_Vehicle_2024 Project'::'eRod_Autonomous_Vehicle_2024'::'System Analysis'::'System Functions'::'Root System Function'.'Adaptive Cruise Control (ACC)'.'7822bc46-8afb-46ec-92df-f20514412b82'
                            to  target ::> 'eRod_Autonomous_Vehicle_2024 Project'::'eRod_Autonomous_Vehicle_2024'::'System Analysis'::'System Functions'::'Root System Function'.'Adaptive Cruise Control (ACC)'.'500d22c2-d370-4952-a64e-c040a85f2de9' {

                                ref :>> involved = 'eRod_Autonomous_Vehicle_2024 Project'::'eRod_Autonomous_Vehicle_2024'::'System Analysis'::'System Functions'::'Root System Function'.'93bef316-12ff-4d4d-97f6-8f2b25851a14';

                            } 
                        ref action 'ca46d716-cc62-4150-b707-7a5c477326b7' = 'eRod_Autonomous_Vehicle_2024 Project'::'eRod_Autonomous_Vehicle_2024'::'System Analysis'::'System Functions'::'Root System Function'.'Provide target vehicle velocity'; 
                        connection '20c56055-1bb7-4903-956f-d70416ab887a' : FunctionalChainInvolvementLink 
                            connect source ::> 'eRod_Autonomous_Vehicle_2024 Project'::'eRod_Autonomous_Vehicle_2024'::'System Analysis'::'System Functions'::'Root System Function'.'Adaptive Cruise Control (ACC)'.'ca46d716-cc62-4150-b707-7a5c477326b7'
                            to  target ::> 'eRod_Autonomous_Vehicle_2024 Project'::'eRod_Autonomous_Vehicle_2024'::'System Analysis'::'System Functions'::'Root System Function'.'Adaptive Cruise Control (ACC)'.'947c1529-2c48-4fb2-b14b-1d3e2c8e45d4' {

                                ref :>> involved = 'eRod_Autonomous_Vehicle_2024 Project'::'eRod_Autonomous_Vehicle_2024'::'System Analysis'::'System Functions'::'Root System Function'.'05f79245-612a-49e4-a3e6-518284f38939';

                            } 
                        ref action 'a4d63bef-65df-4ed8-871c-275617971f76' = 'eRod_Autonomous_Vehicle_2024 Project'::'eRod_Autonomous_Vehicle_2024'::'System Analysis'::'System Functions'::'Root System Function'.'Provide target vehicle velocity'; 
                        connection '4bb6a3a1-9456-4297-8be5-408dc25f2724' : FunctionalChainInvolvementLink 
                            connect source ::> 'eRod_Autonomous_Vehicle_2024 Project'::'eRod_Autonomous_Vehicle_2024'::'System Analysis'::'System Functions'::'Root System Function'.'Adaptive Cruise Control (ACC)'.'a4d63bef-65df-4ed8-871c-275617971f76'
                            to  target ::> 'eRod_Autonomous_Vehicle_2024 Project'::'eRod_Autonomous_Vehicle_2024'::'System Analysis'::'System Functions'::'Root System Function'.'Adaptive Cruise Control (ACC)'.'947c1529-2c48-4fb2-b14b-1d3e2c8e45d4' {

                                ref :>> involved = 'eRod_Autonomous_Vehicle_2024 Project'::'eRod_Autonomous_Vehicle_2024'::'System Analysis'::'System Functions'::'Root System Function'.'cbfb0986-caef-4d30-a0d0-4180ce54e33b';

                            } 
                    }  
                    action 'Lane Keep Assist (LKA)' : FunctionalChain  { 
                        @CapellaID { eid = "65a5554f-5bc2-488f-89ed-985ea8c46d43"; } 
                        attribute :>> kind = FunctionalChainKind::SIMPLE; 
                        connection '4272ed46-c604-4676-be4e-eba95d6e5d22' : FunctionalChainInvolvementLink 
                            connect source ::> 'eRod_Autonomous_Vehicle_2024 Project'::'eRod_Autonomous_Vehicle_2024'::'System Analysis'::'System Functions'::'Root System Function'.'Lane Keep Assist (LKA)'.'f0f4661d-d223-4b4d-baf6-020229160684'
                            to  target ::> 'eRod_Autonomous_Vehicle_2024 Project'::'eRod_Autonomous_Vehicle_2024'::'System Analysis'::'System Functions'::'Root System Function'.'Lane Keep Assist (LKA)'.'d363535a-429f-4134-8120-5fc8292e550c' {

                                ref :>> involved = 'eRod_Autonomous_Vehicle_2024 Project'::'eRod_Autonomous_Vehicle_2024'::'System Analysis'::'System Functions'::'Root System Function'.'df9a5824-6a0e-4e78-8838-7952aebb53f8';

                            } 
                        ref action 'd363535a-429f-4134-8120-5fc8292e550c' = 'eRod_Autonomous_Vehicle_2024 Project'::'eRod_Autonomous_Vehicle_2024'::'System Analysis'::'System Functions'::'Root System Function'.'Detect road'; 
                        ref action 'f0f4661d-d223-4b4d-baf6-020229160684' = 'eRod_Autonomous_Vehicle_2024 Project'::'eRod_Autonomous_Vehicle_2024'::'System Analysis'::'System Functions'::'Root System Function'.'Provide road markers'; 
                        connection '95cca13f-6bf2-4b71-8c2c-178b5c5f83c0' : FunctionalChainInvolvementLink 
                            connect source ::> 'eRod_Autonomous_Vehicle_2024 Project'::'eRod_Autonomous_Vehicle_2024'::'System Analysis'::'System Functions'::'Root System Function'.'Lane Keep Assist (LKA)'.'d363535a-429f-4134-8120-5fc8292e550c'
                            to  target ::> 'eRod_Autonomous_Vehicle_2024 Project'::'eRod_Autonomous_Vehicle_2024'::'System Analysis'::'System Functions'::'Root System Function'.'Lane Keep Assist (LKA)'.'3a351322-d602-41fe-aaf3-c19d89cde24e' {

                                ref :>> involved = 'eRod_Autonomous_Vehicle_2024 Project'::'eRod_Autonomous_Vehicle_2024'::'System Analysis'::'System Functions'::'Root System Function'.'08aed0f8-12c4-4b63-bde1-3d04cbffd737';

                            } 
                        ref action '3a351322-d602-41fe-aaf3-c19d89cde24e' = 'eRod_Autonomous_Vehicle_2024 Project'::'eRod_Autonomous_Vehicle_2024'::'System Analysis'::'System Functions'::'Root System Function'.'Automatic Steering'; 
                        connection '20ff7a5f-1038-45fe-9574-f809e61cd4be' : FunctionalChainInvolvementLink 
                            connect source ::> 'eRod_Autonomous_Vehicle_2024 Project'::'eRod_Autonomous_Vehicle_2024'::'System Analysis'::'System Functions'::'Root System Function'.'Lane Keep Assist (LKA)'.'3a351322-d602-41fe-aaf3-c19d89cde24e'
                            to  target ::> 'eRod_Autonomous_Vehicle_2024 Project'::'eRod_Autonomous_Vehicle_2024'::'System Analysis'::'System Functions'::'Root System Function'.'Lane Keep Assist (LKA)'.'c245a2c5-e0a7-42e3-a7f2-d9a661aff514' {

                                ref :>> involved = 'eRod_Autonomous_Vehicle_2024 Project'::'eRod_Autonomous_Vehicle_2024'::'System Analysis'::'System Functions'::'Root System Function'.'4d771303-3927-4acb-811e-dfc862f247c1';

                            } 
                        ref action 'c245a2c5-e0a7-42e3-a7f2-d9a661aff514' = 'eRod_Autonomous_Vehicle_2024 Project'::'eRod_Autonomous_Vehicle_2024'::'System Analysis'::'System Functions'::'Root System Function'.'Steer wheels'; 
                    }  
                    action 'Vehicle Steering' : FunctionalChain  { 
                        @CapellaID { eid = "20f19f6a-49aa-4b65-926f-e498095d33c5"; } 
                        attribute :>> kind = FunctionalChainKind::SIMPLE; 
                        connection '019ef7b0-6f53-4626-be18-8aa679aef169' : FunctionalChainInvolvementLink 
                            connect source ::> 'eRod_Autonomous_Vehicle_2024 Project'::'eRod_Autonomous_Vehicle_2024'::'System Analysis'::'System Functions'::'Root System Function'.'Vehicle Steering'.'cce4b297-8a99-43ab-a234-554a04c22549'
                            to  target ::> 'eRod_Autonomous_Vehicle_2024 Project'::'eRod_Autonomous_Vehicle_2024'::'System Analysis'::'System Functions'::'Root System Function'.'Vehicle Steering'.'a121b0f8-410d-422a-8e42-1028192fda67' {

                                ref :>> involved = 'eRod_Autonomous_Vehicle_2024 Project'::'eRod_Autonomous_Vehicle_2024'::'System Analysis'::'System Functions'::'Root System Function'.'ed11051f-31d8-4e63-b54b-0a3ab5d8bb79';

                            } 
                        ref action 'a121b0f8-410d-422a-8e42-1028192fda67' = 'eRod_Autonomous_Vehicle_2024 Project'::'eRod_Autonomous_Vehicle_2024'::'System Analysis'::'System Functions'::'Root System Function'.'Steer wheels'; 
                        ref action 'cce4b297-8a99-43ab-a234-554a04c22549' = 'eRod_Autonomous_Vehicle_2024 Project'::'eRod_Autonomous_Vehicle_2024'::'System Analysis'::'System Functions'::'Root System Function'.'Drive vehicle'; 
                        connection 'c54b5821-c957-4980-b9a1-fa1405c4b7d1' : FunctionalChainInvolvementLink 
                            connect source ::> 'eRod_Autonomous_Vehicle_2024 Project'::'eRod_Autonomous_Vehicle_2024'::'System Analysis'::'System Functions'::'Root System Function'.'Vehicle Steering'.'a121b0f8-410d-422a-8e42-1028192fda67'
                            to  target ::> 'eRod_Autonomous_Vehicle_2024 Project'::'eRod_Autonomous_Vehicle_2024'::'System Analysis'::'System Functions'::'Root System Function'.'Vehicle Steering'.'762b651b-a498-49df-bff3-567c8382b7d8' {

                                ref :>> involved = 'eRod_Autonomous_Vehicle_2024 Project'::'eRod_Autonomous_Vehicle_2024'::'System Analysis'::'System Functions'::'Root System Function'.'e1303971-951c-44f8-b2c2-4482427ada98';

                            } 
                        ref action '762b651b-a498-49df-bff3-567c8382b7d8' = 'eRod_Autonomous_Vehicle_2024 Project'::'eRod_Autonomous_Vehicle_2024'::'System Analysis'::'System Functions'::'Root System Function'.'Resist Front Wheels'; 
                    }  
                    action 'Remote Park' : FunctionalChain  { 
                        @CapellaID { eid = "dac1a8b7-4fac-4e2e-a155-a8abbe15f7b3"; } 
                        attribute :>> kind = FunctionalChainKind::SIMPLE; 
                        connection '2f55a980-5a78-4ff7-8de7-2456023c04ab' : FunctionalChainInvolvementLink 
                            connect source ::> 'eRod_Autonomous_Vehicle_2024 Project'::'eRod_Autonomous_Vehicle_2024'::'System Analysis'::'System Functions'::'Root System Function'.'Remote Park'.'e4856a74-cafb-4f91-a18f-7851c0e6accc'
                            to  target ::> 'eRod_Autonomous_Vehicle_2024 Project'::'eRod_Autonomous_Vehicle_2024'::'System Analysis'::'System Functions'::'Root System Function'.'Remote Park'.'512c438a-3bcc-4b8d-94ce-b50164d7e292' {

                                ref :>> involved = 'eRod_Autonomous_Vehicle_2024 Project'::'eRod_Autonomous_Vehicle_2024'::'System Analysis'::'System Functions'::'Root System Function'.'ee54ddae-801f-48a9-83d6-aa89a303ff38';

                            } 
                        ref action '512c438a-3bcc-4b8d-94ce-b50164d7e292' = 'eRod_Autonomous_Vehicle_2024 Project'::'eRod_Autonomous_Vehicle_2024'::'System Analysis'::'System Functions'::'Root System Function'.'Remote Operate Car'; 
                        ref action 'e4856a74-cafb-4f91-a18f-7851c0e6accc' = 'eRod_Autonomous_Vehicle_2024 Project'::'eRod_Autonomous_Vehicle_2024'::'System Analysis'::'System Functions'::'Root System Function'.'Vehicle Command'; 
                        connection '0c2274b1-5f1b-4bd2-b591-de2109ba349b' : FunctionalChainInvolvementLink 
                            connect source ::> 'eRod_Autonomous_Vehicle_2024 Project'::'eRod_Autonomous_Vehicle_2024'::'System Analysis'::'System Functions'::'Root System Function'.'Remote Park'.'512c438a-3bcc-4b8d-94ce-b50164d7e292'
                            to  target ::> 'eRod_Autonomous_Vehicle_2024 Project'::'eRod_Autonomous_Vehicle_2024'::'System Analysis'::'System Functions'::'Root System Function'.'Remote Park'.'81f78e69-51f9-46e0-8dff-82eb0262ae3b' {

                                ref :>> involved = 'eRod_Autonomous_Vehicle_2024 Project'::'eRod_Autonomous_Vehicle_2024'::'System Analysis'::'System Functions'::'Root System Function'.'f54b0b7a-d8dd-4e96-8a03-c3e3f3516bfc';

                            } 
                        ref action '81f78e69-51f9-46e0-8dff-82eb0262ae3b' = 'eRod_Autonomous_Vehicle_2024 Project'::'eRod_Autonomous_Vehicle_2024'::'System Analysis'::'System Functions'::'Root System Function'.'Park vehicle'; 
                        connection '04cc65b8-31d4-47dd-ac4d-f493f0f0252f' : FunctionalChainInvolvementLink 
                            connect source ::> 'eRod_Autonomous_Vehicle_2024 Project'::'eRod_Autonomous_Vehicle_2024'::'System Analysis'::'System Functions'::'Root System Function'.'Remote Park'.'81f78e69-51f9-46e0-8dff-82eb0262ae3b'
                            to  target ::> 'eRod_Autonomous_Vehicle_2024 Project'::'eRod_Autonomous_Vehicle_2024'::'System Analysis'::'System Functions'::'Root System Function'.'Remote Park'.'9473301f-7b41-43f1-8c61-3d8376f2fceb' {

                                ref :>> involved = 'eRod_Autonomous_Vehicle_2024 Project'::'eRod_Autonomous_Vehicle_2024'::'System Analysis'::'System Functions'::'Root System Function'.'1bcefe26-eb27-4aad-adb4-d8dcba87b460';

                            } 
                        ref action '9473301f-7b41-43f1-8c61-3d8376f2fceb' = 'eRod_Autonomous_Vehicle_2024 Project'::'eRod_Autonomous_Vehicle_2024'::'System Analysis'::'System Functions'::'Root System Function'.'Control braking'; 
                        connection '75d4347a-9a3a-4adc-97c3-0ee9cc860f1e' : FunctionalChainInvolvementLink 
                            connect source ::> 'eRod_Autonomous_Vehicle_2024 Project'::'eRod_Autonomous_Vehicle_2024'::'System Analysis'::'System Functions'::'Root System Function'.'Remote Park'.'81f78e69-51f9-46e0-8dff-82eb0262ae3b'
                            to  target ::> 'eRod_Autonomous_Vehicle_2024 Project'::'eRod_Autonomous_Vehicle_2024'::'System Analysis'::'System Functions'::'Root System Function'.'Remote Park'.'29edcbcd-6b7c-4b77-b36b-455d08b709f8' {

                                ref :>> involved = 'eRod_Autonomous_Vehicle_2024 Project'::'eRod_Autonomous_Vehicle_2024'::'System Analysis'::'System Functions'::'Root System Function'.'5df12483-df3d-4b7d-98bc-7ad4c7c340a9';

                            } 
                        ref action '29edcbcd-6b7c-4b77-b36b-455d08b709f8' = 'eRod_Autonomous_Vehicle_2024 Project'::'eRod_Autonomous_Vehicle_2024'::'System Analysis'::'System Functions'::'Root System Function'.'Steer Wheels Remote'; 
                        connection '5d75a218-044c-455e-bfbf-8fb11eea2f13' : FunctionalChainInvolvementLink 
                            connect source ::> 'eRod_Autonomous_Vehicle_2024 Project'::'eRod_Autonomous_Vehicle_2024'::'System Analysis'::'System Functions'::'Root System Function'.'Remote Park'.'29edcbcd-6b7c-4b77-b36b-455d08b709f8'
                            to  target ::> 'eRod_Autonomous_Vehicle_2024 Project'::'eRod_Autonomous_Vehicle_2024'::'System Analysis'::'System Functions'::'Root System Function'.'Remote Park'.'307eced5-b7a6-4d42-813a-391e42c3dcee' {

                                ref :>> involved = 'eRod_Autonomous_Vehicle_2024 Project'::'eRod_Autonomous_Vehicle_2024'::'System Analysis'::'System Functions'::'Root System Function'.'42ba7b49-d3bd-432e-b45d-12c7648470ea';

                            } 
                        ref action '307eced5-b7a6-4d42-813a-391e42c3dcee' = 'eRod_Autonomous_Vehicle_2024 Project'::'eRod_Autonomous_Vehicle_2024'::'System Analysis'::'System Functions'::'Root System Function'.'Deliver traction to surface'; 
                        connection 'ed1da97b-2d52-45bf-8635-3b41f967728e' : FunctionalChainInvolvementLink 
                            connect source ::> 'eRod_Autonomous_Vehicle_2024 Project'::'eRod_Autonomous_Vehicle_2024'::'System Analysis'::'System Functions'::'Root System Function'.'Remote Park'.'307eced5-b7a6-4d42-813a-391e42c3dcee'
                            to  target ::> 'eRod_Autonomous_Vehicle_2024 Project'::'eRod_Autonomous_Vehicle_2024'::'System Analysis'::'System Functions'::'Root System Function'.'Remote Park'.'850bc0f3-cd2f-4d37-9d2b-c291116a4ad9' {

                                ref :>> involved = 'eRod_Autonomous_Vehicle_2024 Project'::'eRod_Autonomous_Vehicle_2024'::'System Analysis'::'System Functions'::'Root System Function'.'c57c6fd8-1cfb-4f41-87ea-4b32a2a8f214';

                            } 
                        ref action '850bc0f3-cd2f-4d37-9d2b-c291116a4ad9' = 'eRod_Autonomous_Vehicle_2024 Project'::'eRod_Autonomous_Vehicle_2024'::'System Analysis'::'System Functions'::'Root System Function'.'Provide diverse terrain'; 
                        ref action 'eb61bd78-7416-489b-b467-30800acfeda5' = 'eRod_Autonomous_Vehicle_2024 Project'::'eRod_Autonomous_Vehicle_2024'::'System Analysis'::'System Functions'::'Root System Function'.'Status and command indication'; 
                        connection 'e92640ac-7904-4ab6-9259-19dcb61aa04c' : FunctionalChainInvolvementLink 
                            connect source ::> 'eRod_Autonomous_Vehicle_2024 Project'::'eRod_Autonomous_Vehicle_2024'::'System Analysis'::'System Functions'::'Root System Function'.'Remote Park'.'eb61bd78-7416-489b-b467-30800acfeda5'
                            to  target ::> 'eRod_Autonomous_Vehicle_2024 Project'::'eRod_Autonomous_Vehicle_2024'::'System Analysis'::'System Functions'::'Root System Function'.'Remote Park'.'81f78e69-51f9-46e0-8dff-82eb0262ae3b' {

                                ref :>> involved = 'eRod_Autonomous_Vehicle_2024 Project'::'eRod_Autonomous_Vehicle_2024'::'System Analysis'::'System Functions'::'Root System Function'.'791adf23-46b4-42ab-8846-0146cf2a19b9';

                            } 
                        ref action '7572af42-a414-4916-99d4-084e50166d04' = 'eRod_Autonomous_Vehicle_2024 Project'::'eRod_Autonomous_Vehicle_2024'::'System Analysis'::'System Functions'::'Root System Function'.'Receive Status of Progess '; 
                        connection 'e6d5878f-bc36-4c0b-a931-48f00ac798c4' : FunctionalChainInvolvementLink 
                            connect source ::> 'eRod_Autonomous_Vehicle_2024 Project'::'eRod_Autonomous_Vehicle_2024'::'System Analysis'::'System Functions'::'Root System Function'.'Remote Park'.'eb61bd78-7416-489b-b467-30800acfeda5'
                            to  target ::> 'eRod_Autonomous_Vehicle_2024 Project'::'eRod_Autonomous_Vehicle_2024'::'System Analysis'::'System Functions'::'Root System Function'.'Remote Park'.'7572af42-a414-4916-99d4-084e50166d04' {

                                ref :>> involved = 'eRod_Autonomous_Vehicle_2024 Project'::'eRod_Autonomous_Vehicle_2024'::'System Analysis'::'System Functions'::'Root System Function'.'7e53f548-8875-4753-827e-0c3137930f91';

                            } 
                         
                    }  
                    action 'Drive on a race track' : SystemFunction  { 
                        @CapellaID { eid = "0a01d6b4-d07c-4f5d-8d43-ec62462ac1de"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outCommand' : FunctionOutputPort  { 
                            @CapellaID { eid = "5b2c9d60-91a0-4ddd-a08e-e1d694ea6e14"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Drive on a race track'.'outCommand'); 
                    }  
                    action 'Sporty drive' : SystemFunction  { 
                        @CapellaID { eid = "1d84b39b-4d90-4190-b9c5-90bbd439b67a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outCause' : FunctionOutputPort  { 
                            @CapellaID { eid = "ae310c16-97e7-4e9a-9715-36bbd5fa84fc"; } 
                            attribute :>> isControl = false; 
                            attribute :>> isControlType = false; 
                            attribute :>> kindOfNode = ObjectNodeKind::Unspecified; 
                            attribute :>> ordering = ObjectNodeOrderingKind::FIFO; 
                        }  
                        out port 'FOP 2' : FunctionOutputPort  { 
                            @CapellaID { eid = "b1acc93e-1f3f-4fd3-b837-817e17b46f5b"; } 
                            attribute :>> isControl = false; 
                            attribute :>> isControlType = false; 
                            attribute :>> kindOfNode = ObjectNodeKind::Unspecified; 
                            attribute :>> ordering = ObjectNodeOrderingKind::FIFO; 
                        }  
                        in port 'FIP 3' : FunctionInputPort  { 
                            @CapellaID { eid = "84ab9c91-f328-4bb6-9d0f-e47deb10f54c"; } 
                            attribute :>> isControl = false; 
                            attribute :>> isControlType = false; 
                            attribute :>> kindOfNode = ObjectNodeKind::Unspecified; 
                            attribute :>> ordering = ObjectNodeOrderingKind::FIFO; 
                        }  
                        in port 'inCommand' : FunctionInputPort  { 
                            @CapellaID { eid = "0580a909-1686-4e56-a9b9-e0dacd7b0ae1"; } 
                            attribute :>> isControl = false; 
                            attribute :>> isControlType = false; 
                            attribute :>> kindOfNode = ObjectNodeKind::Unspecified; 
                            attribute :>> ordering = ObjectNodeOrderingKind::FIFO; 
                        }  
                        in port 'inRe-enable' : FunctionInputPort  { 
                            @CapellaID { eid = "3fcd1dd3-2641-441f-aad0-d16ede3f01cc"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Sporty drive'.'outCause',
                        'eRod_Autonomous_Vehicle_2024 Project'::'eRod_Autonomous_Vehicle_2024'::'System Analysis'::'System Functions'::'Root System Function'.'Sporty drive'.'FOP 2'); 
                        ref :>> inputs =  ('eRod_Autonomous_Vehicle_2024 Project'::'eRod_Autonomous_Vehicle_2024'::'System Analysis'::'System Functions'::'Root System Function'.'Sporty drive'.'FIP 3',
                        'eRod_Autonomous_Vehicle_2024 Project'::'eRod_Autonomous_Vehicle_2024'::'System Analysis'::'System Functions'::'Root System Function'.'Sporty drive'.'inCommand',
                        'eRod_Autonomous_Vehicle_2024 Project'::'eRod_Autonomous_Vehicle_2024'::'System Analysis'::'System Functions'::'Root System Function'.'Sporty drive'.'inRe-enable'); 
                    }  
                    action 'Car racing experience absorbed' : SystemFunction  { 
                        @CapellaID { eid = "d87d0762-b9bf-4e4e-8423-4f36698c351b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'inProvide' : FunctionInputPort  { 
                            @CapellaID { eid = "51b36870-1c85-4dc3-8a18-d553b51d8368"; } 
                            attribute :>> isControl = false; 
                            attribute :>> isControlType = false; 
                            attribute :>> kindOfNode = ObjectNodeKind::Unspecified; 
                            attribute :>> ordering = ObjectNodeOrderingKind::FIFO; 
                        }  
                         
                        ref :>> inputs =  ('eRod_Autonomous_Vehicle_2024 Project'::'eRod_Autonomous_Vehicle_2024'::'System Analysis'::'System Functions'::'Root System Function'.'Car racing experience absorbed'.'inProvide'); 
                    }  
                    action 'Motor overheating warning ' : SystemFunction  { 
                        @CapellaID { eid = "5ca6807a-0922-4a39-82f5-129498f99ca8"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outDisplay' : FunctionOutputPort  { 
                            @CapellaID { eid = "0a7946d5-0c69-44be-9abb-bde09be15353"; } 
                            attribute :>> isControl = false; 
                            attribute :>> isControlType = false; 
                            attribute :>> kindOfNode = ObjectNodeKind::Unspecified; 
                            attribute :>> ordering = ObjectNodeOrderingKind::FIFO; 
                        }  
                        in port 'inCause' : FunctionInputPort  { 
                            @CapellaID { eid = "5d65ff4b-fbac-40b5-bca5-78a84129a472"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Motor overheating warning '.'outDisplay'); 
                        ref :>> inputs =  ('eRod_Autonomous_Vehicle_2024 Project'::'eRod_Autonomous_Vehicle_2024'::'System Analysis'::'System Functions'::'Root System Function'.'Motor overheating warning '.'inCause'); 
                    }  
                    action 'Software update' : SystemFunction  { 
                        @CapellaID { eid = "9218fb32-0340-4a42-b71c-918005e02264"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'Signal' : FunctionOutputPort  { 
                            @CapellaID { eid = "da979439-c18a-45bd-94e7-3e79be3d83da"; } 
                            attribute :>> isControl = false; 
                            attribute :>> isControlType = false; 
                            attribute :>> kindOfNode = ObjectNodeKind::Unspecified; 
                            attribute :>> ordering = ObjectNodeOrderingKind::FIFO; 
                        }  
                        out port 'outRe-enable' : FunctionOutputPort  { 
                            @CapellaID { eid = "e4e28a0e-e8b7-4ae7-a569-3fe5ec90fc6a"; } 
                            attribute :>> isControl = false; 
                            attribute :>> isControlType = false; 
                            attribute :>> kindOfNode = ObjectNodeKind::Unspecified; 
                            attribute :>> ordering = ObjectNodeOrderingKind::FIFO; 
                        }  
                        in port 'inApproval' : FunctionInputPort  { 
                            @CapellaID { eid = "5c7db013-3086-49e3-af38-414987009a9c"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Software update'.'Signal',
                        'eRod_Autonomous_Vehicle_2024 Project'::'eRod_Autonomous_Vehicle_2024'::'System Analysis'::'System Functions'::'Root System Function'.'Software update'.'outRe-enable'); 
                        ref :>> inputs =  ('eRod_Autonomous_Vehicle_2024 Project'::'eRod_Autonomous_Vehicle_2024'::'System Analysis'::'System Functions'::'Root System Function'.'Software update'.'inApproval'); 
                    }  
                    action 'Report issues' : SystemFunction  { 
                        @CapellaID { eid = "23b17046-6f56-47df-9e23-4a12a6e96f69"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "1daecc25-7014-4813-a6d6-f447386cec71"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "2451ac68-ca71-46f6-a556-93314a5cf410"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Report issues'.'FOP 1'); 
                        ref :>> inputs =  ('eRod_Autonomous_Vehicle_2024 Project'::'eRod_Autonomous_Vehicle_2024'::'System Analysis'::'System Functions'::'Root System Function'.'Report issues'.'FIP 1'); 
                    }  
                    action 'Get informed with issues' : SystemFunction  { 
                        @CapellaID { eid = "afcaa94e-8070-4399-a368-bf5ba1509d8b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "3cb7e108-a555-4102-98fc-4292fd208382"; } 
                            attribute :>> isControl = false; 
                            attribute :>> isControlType = false; 
                            attribute :>> kindOfNode = ObjectNodeKind::Unspecified; 
                            attribute :>> ordering = ObjectNodeOrderingKind::FIFO; 
                        }  
                        in port 'inDisplay' : FunctionInputPort  { 
                            @CapellaID { eid = "c20548ec-af69-44b3-a8f3-ce9e3aa6b1e7"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'System Analysis'::'System Functions'::'Root System Function'.'Get informed with issues'.'FOP 1'); 
                        ref :>> inputs =  ('eRod_Autonomous_Vehicle_2024 Project'::'eRod_Autonomous_Vehicle_2024'::'System Analysis'::'System Functions'::'Root System Function'.'Get informed with issues'.'inDisplay'); 
                    }  
                    action 'Deaccelerate' : SystemFunction  { 
                        @CapellaID { eid = "75ddac84-c274-4bf5-b912-9fc3a5d608c7"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "e9cfe7a0-7cab-471d-a4c3-c7df591fe167"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "0ae22eb5-81b4-4388-a8dc-6fc1e484df9d"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'System Analysis'::'System Functions'::'Root System Function'.'Deaccelerate'.'FOP 1'); 
                        ref :>> inputs =  ('eRod_Autonomous_Vehicle_2024 Project'::'eRod_Autonomous_Vehicle_2024'::'System Analysis'::'System Functions'::'Root System Function'.'Deaccelerate'.'FIP 1'); 
                    }  
                    action 'Stop' : SystemFunction  { 
                        @CapellaID { eid = "acdbc383-1d78-4382-8490-950beca7eca6"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outProvide' : FunctionOutputPort  { 
                            @CapellaID { eid = "82071b8f-a8e3-40f9-ada4-f534e3e5dd6f"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "396ef194-37f0-40f7-887e-4a6274ca94f7"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'System Analysis'::'System Functions'::'Root System Function'.'Stop'.'outProvide'); 
                        ref :>> inputs =  ('eRod_Autonomous_Vehicle_2024 Project'::'eRod_Autonomous_Vehicle_2024'::'System Analysis'::'System Functions'::'Root System Function'.'Stop'.'FIP 1'); 
                    }  
                    action 'Get Software-update' : SystemFunction  { 
                        @CapellaID { eid = "929a0f05-f489-460c-a2b8-4a3f3fe912c3"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "65eada8a-6de3-421d-b75d-b3e427bce5c0"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "fce45272-16e7-4913-bf02-ecedd02bdcc9"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'System Analysis'::'System Functions'::'Root System Function'.'Get Software-update'.'FOP 1'); 
                        ref :>> inputs =  ('eRod_Autonomous_Vehicle_2024 Project'::'eRod_Autonomous_Vehicle_2024'::'System Analysis'::'System Functions'::'Root System Function'.'Get Software-update'.'FIP 1'); 
                    }  
                    action 'Obtain car racing experience' : SystemFunction  { 
                        @CapellaID { eid = "f000ebf7-e605-463c-9a06-83abed2a8648"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "e47af8c5-9d5b-4de6-be0c-06ec479170e7"; } 
                            attribute :>> isControl = false; 
                            attribute :>> isControlType = false; 
                            attribute :>> kindOfNode = ObjectNodeKind::Unspecified; 
                            attribute :>> ordering = ObjectNodeOrderingKind::FIFO; 
                        }  
                        ref :>> inputs =  ('eRod_Autonomous_Vehicle_2024 Project'::'eRod_Autonomous_Vehicle_2024'::'System Analysis'::'System Functions'::'Root System Function'.'Obtain car racing experience'.'FIP 1'); 
                    }  
                    action 'Transfer Energy' : SystemFunction  { 
                        @CapellaID { eid = "737357de-de4d-4691-9758-da4517f7edaa"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Acquire Energy' : SystemFunction  { 
                            @CapellaID { eid = "23c98182-0dd0-4b54-a68e-500c93905b0f"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "ecc7d737-a66d-41e1-b9b9-8cf1320ed0ec"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "ea07100c-452e-4dd8-94a6-f33463cfdeae"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'System Analysis'::'System Functions'::'Root System Function'.'Transfer Energy'.'Acquire Energy'.'FOP 1'); 
                            ref :>> inputs =  ('eRod_Autonomous_Vehicle_2024 Project'::'eRod_Autonomous_Vehicle_2024'::'System Analysis'::'System Functions'::'Root System Function'.'Transfer Energy'.'Acquire Energy'.'FIP 1'); 
                        }  
                        action 'Tranfer electrical energy into mechanical energy' : SystemFunction  { 
                            @CapellaID { eid = "916f1cea-ac74-4604-a7c0-1745bbb1ade7"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "9a8e9636-23fc-42b0-9b99-113d9f0a7f5b"; } 
                                attribute :>> isControl = false; 
                                attribute :>> isControlType = false; 
                                attribute :>> kindOfNode = ObjectNodeKind::Unspecified; 
                                attribute :>> ordering = ObjectNodeOrderingKind::FIFO; 
                            }  
                            out port 'FOP 2' : FunctionOutputPort  { 
                                @CapellaID { eid = "6ef83b5a-164e-4059-a5c6-4c228b1c001e"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "29070c87-4d37-4d31-b095-1041bb6b4d44"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'System Analysis'::'System Functions'::'Root System Function'.'Transfer Energy'.'Tranfer electrical energy into mechanical energy'.'FOP 1',
                            'eRod_Autonomous_Vehicle_2024 Project'::'eRod_Autonomous_Vehicle_2024'::'System Analysis'::'System Functions'::'Root System Function'.'Transfer Energy'.'Tranfer electrical energy into mechanical energy'.'FOP 2'); 
                            ref :>> inputs =  ('eRod_Autonomous_Vehicle_2024 Project'::'eRod_Autonomous_Vehicle_2024'::'System Analysis'::'System Functions'::'Root System Function'.'Transfer Energy'.'Tranfer electrical energy into mechanical energy'.'FIP 1'); 
                        }  
                        action 'generate power' : SystemFunction  { 
                            @CapellaID { eid = "88fc9b9c-73ff-47c9-a34b-6a7bbb4393d9"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "ac57a7bb-9b83-458a-82ef-cacc7a766f94"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "5d2ac288-7c4c-40f5-9e60-cf1d50d6435f"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'System Analysis'::'System Functions'::'Root System Function'.'Transfer Energy'.'generate power'.'FOP 1'); 
                            ref :>> inputs =  ('eRod_Autonomous_Vehicle_2024 Project'::'eRod_Autonomous_Vehicle_2024'::'System Analysis'::'System Functions'::'Root System Function'.'Transfer Energy'.'generate power'.'FIP 1'); 
                        }  
                        action 'Generate heat' : SystemFunction  { 
                            @CapellaID { eid = "bc19439a-b5ab-46c0-a49e-cab1203c8d69"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "06c39cc6-9036-40d8-8ed2-264271565f08"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "4ecdc934-9efe-4ce3-8616-fd42da961e3b"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'System Analysis'::'System Functions'::'Root System Function'.'Transfer Energy'.'Generate heat'.'FOP 1'); 
                            ref :>> inputs =  ('eRod_Autonomous_Vehicle_2024 Project'::'eRod_Autonomous_Vehicle_2024'::'System Analysis'::'System Functions'::'Root System Function'.'Transfer Energy'.'Generate heat'.'FIP 1'); 
                        }  
                        interface 'cfeffdb3-21f9-4dba-9ed3-1a80cfd0de71' : FunctionalExchange 
                            connect source ::> 'eRod_Autonomous_Vehicle_2024 Project'::'eRod_Autonomous_Vehicle_2024'::'System Analysis'::'System Functions'::'Root System Function'.'Transfer Energy'.'Acquire Energy'.'FOP 1'
                            to target ::> 'eRod_Autonomous_Vehicle_2024 Project'::'eRod_Autonomous_Vehicle_2024'::'System Analysis'::'System Functions'::'Root System Function'.'Transfer Energy'.'Tranfer electrical energy into mechanical energy'.'FIP 1' { 
                            @CapellaID { eid = "cfeffdb3-21f9-4dba-9ed3-1a80cfd0de71"; } 
                            attribute :>> isMulticast = false; 
                            attribute :>> isMultireceive = false; 
                            attribute :>> kindOfRate = RateKind::Unspecified; 
                            attribute :>> interfaceName = "Energy"; 
                        }  
                        interface 'b2a28595-ce9f-44d9-854e-a10d0aa34bd2' : FunctionalExchange 
                            connect source ::> 'eRod_Autonomous_Vehicle_2024 Project'::'eRod_Autonomous_Vehicle_2024'::'System Analysis'::'System Functions'::'Root System Function'.'Transfer Energy'.'Tranfer electrical energy into mechanical energy'.'FOP 1'
                            to target ::> 'eRod_Autonomous_Vehicle_2024 Project'::'eRod_Autonomous_Vehicle_2024'::'System Analysis'::'System Functions'::'Root System Function'.'Transfer Energy'.'generate power'.'FIP 1' { 
                            @CapellaID { eid = "b2a28595-ce9f-44d9-854e-a10d0aa34bd2"; } 
                            attribute :>> isMulticast = false; 
                            attribute :>> isMultireceive = false; 
                            attribute :>> kindOfRate = RateKind::Unspecified; 
                            attribute :>> interfaceName = "Energy"; 
                        }  
                        interface '9e076827-cd80-4f42-9899-127265c6a576' : FunctionalExchange 
                            connect source ::> 'eRod_Autonomous_Vehicle_2024 Project'::'eRod_Autonomous_Vehicle_2024'::'System Analysis'::'System Functions'::'Root System Function'.'Transfer Energy'.'Tranfer electrical energy into mechanical energy'.'FOP 2'
                            to target ::> 'eRod_Autonomous_Vehicle_2024 Project'::'eRod_Autonomous_Vehicle_2024'::'System Analysis'::'System Functions'::'Root System Function'.'Transfer Energy'.'Generate heat'.'FIP 1' { 
                            @CapellaID { eid = "9e076827-cd80-4f42-9899-127265c6a576"; } 
                            attribute :>> isMulticast = false; 
                            attribute :>> isMultireceive = false; 
                            attribute :>> kindOfRate = RateKind::Unspecified; 
                            attribute :>> interfaceName = "Energy"; 
                        }  
                        ref :>> ownedFunctions =  ('eRod_Autonomous_Vehicle_2024 Project'::'eRod_Autonomous_Vehicle_2024'::'System Analysis'::'System Functions'::'Root System Function'.'Transfer Energy'.'Acquire Energy',
                        'eRod_Autonomous_Vehicle_2024 Project'::'eRod_Autonomous_Vehicle_2024'::'System Analysis'::'System Functions'::'Root System Function'.'Transfer Energy'.'Tranfer electrical energy into mechanical energy',
                        'eRod_Autonomous_Vehicle_2024 Project'::'eRod_Autonomous_Vehicle_2024'::'System Analysis'::'System Functions'::'Root System Function'.'Transfer Energy'.'generate power',
                        'eRod_Autonomous_Vehicle_2024 Project'::'eRod_Autonomous_Vehicle_2024'::'System Analysis'::'System Functions'::'Root System Function'.'Transfer Energy'.'Generate heat'); 
                        ref :>> ownedFunctionalExchanges =  ('eRod_Autonomous_Vehicle_2024 Project'::'eRod_Autonomous_Vehicle_2024'::'System Analysis'::'System Functions'::'Root System Function'.'Transfer Energy'.'cfeffdb3-21f9-4dba-9ed3-1a80cfd0de71',
                        'eRod_Autonomous_Vehicle_2024 Project'::'eRod_Autonomous_Vehicle_2024'::'System Analysis'::'System Functions'::'Root System Function'.'Transfer Energy'.'b2a28595-ce9f-44d9-854e-a10d0aa34bd2',
                        'eRod_Autonomous_Vehicle_2024 Project'::'eRod_Autonomous_Vehicle_2024'::'System Analysis'::'System Functions'::'Root System Function'.'Transfer Energy'.'9e076827-cd80-4f42-9899-127265c6a576'); 
                    }  
                    action 'Motor protect' : SystemFunction  { 
                        @CapellaID { eid = "eaeca817-e22d-45c6-86c1-fa7c2ecbc99a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Monitor temperature' : SystemFunction  { 
                            @CapellaID { eid = "3f70cf7a-ee51-42a8-a2c4-a38771b084ab"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 2' : FunctionOutputPort  { 
                                @CapellaID { eid = "c743f331-e5e7-4c21-bbe2-ca54dca86f2f"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "40ad6056-2509-4554-a06d-3e4bfdf0a04e"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'System Analysis'::'System Functions'::'Root System Function'.'Motor protect'.'Monitor temperature'.'FOP 2'); 
                            ref :>> inputs =  ('eRod_Autonomous_Vehicle_2024 Project'::'eRod_Autonomous_Vehicle_2024'::'System Analysis'::'System Functions'::'Root System Function'.'Motor protect'.'Monitor temperature'.'FIP 1'); 
                        }  
                        action 'Detect temperature limit' : SystemFunction  { 
                            @CapellaID { eid = "f3316291-7d37-4db5-9ec9-71b8f5c073df"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 3' : FunctionOutputPort  { 
                                @CapellaID { eid = "052db59f-128c-4ec0-b6c7-64c5aec85a39"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "0e4205f7-36d0-4e68-b3f6-770758aa1c15"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'System Analysis'::'System Functions'::'Root System Function'.'Motor protect'.'Detect temperature limit'.'FOP 3'); 
                            ref :>> inputs =  ('eRod_Autonomous_Vehicle_2024 Project'::'eRod_Autonomous_Vehicle_2024'::'System Analysis'::'System Functions'::'Root System Function'.'Motor protect'.'Detect temperature limit'.'FIP 1'); 
                        }  
                        action 'Reduce power' : SystemFunction  { 
                            @CapellaID { eid = "2a47dd1a-1db2-48d3-a8c8-519284147118"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "0bea1f56-86ce-48b9-806e-46958ebb2bca"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "6e6599d7-cf30-491b-89e1-e4a0d777b409"; } 
                                attribute :>> isControl = false; 
                                attribute :>> isControlType = false; 
                                attribute :>> kindOfNode = ObjectNodeKind::Unspecified; 
                                attribute :>> ordering = ObjectNodeOrderingKind::FIFO; 
                            }  
                            in port 'FIP 2' : FunctionInputPort  { 
                                @CapellaID { eid = "e0f676fb-b9d2-4792-bc59-de2e99023a35"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'System Analysis'::'System Functions'::'Root System Function'.'Motor protect'.'Reduce power'.'FOP 1'); 
                            ref :>> inputs =  ('eRod_Autonomous_Vehicle_2024 Project'::'eRod_Autonomous_Vehicle_2024'::'System Analysis'::'System Functions'::'Root System Function'.'Motor protect'.'Reduce power'.'FIP 1',
                            'eRod_Autonomous_Vehicle_2024 Project'::'eRod_Autonomous_Vehicle_2024'::'System Analysis'::'System Functions'::'Root System Function'.'Motor protect'.'Reduce power'.'FIP 2'); 
                        }  
                        interface '2931413b-f2c8-4514-a67c-7126167c0bae' : FunctionalExchange 
                            connect source ::> 'eRod_Autonomous_Vehicle_2024 Project'::'eRod_Autonomous_Vehicle_2024'::'System Analysis'::'System Functions'::'Root System Function'.'Motor protect'.'Monitor temperature'.'FOP 2'
                            to target ::> 'eRod_Autonomous_Vehicle_2024 Project'::'eRod_Autonomous_Vehicle_2024'::'System Analysis'::'System Functions'::'Root System Function'.'Motor protect'.'Detect temperature limit'.'FIP 1' { 
                            @CapellaID { eid = "2931413b-f2c8-4514-a67c-7126167c0bae"; } 
                            attribute :>> isMulticast = false; 
                            attribute :>> isMultireceive = false; 
                            attribute :>> kindOfRate = RateKind::Unspecified; 
                            attribute :>> interfaceName = "Temperature"; 
                        }  
                        ref :>> ownedFunctions =  ('eRod_Autonomous_Vehicle_2024 Project'::'eRod_Autonomous_Vehicle_2024'::'System Analysis'::'System Functions'::'Root System Function'.'Motor protect'.'Monitor temperature',
                        'eRod_Autonomous_Vehicle_2024 Project'::'eRod_Autonomous_Vehicle_2024'::'System Analysis'::'System Functions'::'Root System Function'.'Motor protect'.'Detect temperature limit',
                        'eRod_Autonomous_Vehicle_2024 Project'::'eRod_Autonomous_Vehicle_2024'::'System Analysis'::'System Functions'::'Root System Function'.'Motor protect'.'Reduce power'); 
                        ref :>> ownedFunctionalExchanges =  ('eRod_Autonomous_Vehicle_2024 Project'::'eRod_Autonomous_Vehicle_2024'::'System Analysis'::'System Functions'::'Root System Function'.'Motor protect'.'2931413b-f2c8-4514-a67c-7126167c0bae'); 
                    }  
                    action 'Control temperature' : SystemFunction  { 
                        @CapellaID { eid = "927dbc63-9a6e-4829-9fda-4a6a67befefb"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Limit temperature' : SystemFunction  { 
                            @CapellaID { eid = "43a65724-0627-4a50-9a9f-0e0aafd8f11c"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "a58fef0d-904e-48d0-9bfb-d731630c9e46"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "6e0ad8f3-6a8b-4169-ac5e-91c7a8e2a2e2"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'System Analysis'::'System Functions'::'Root System Function'.'Control temperature'.'Limit temperature'.'FOP 1'); 
                            ref :>> inputs =  ('eRod_Autonomous_Vehicle_2024 Project'::'eRod_Autonomous_Vehicle_2024'::'System Analysis'::'System Functions'::'Root System Function'.'Control temperature'.'Limit temperature'.'FIP 1'); 
                        }  
                        action 'Limit power' : SystemFunction  { 
                            @CapellaID { eid = "a818f691-4ad2-4f98-8988-4776f0a08eff"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "20ec1a81-3878-4e8b-a661-e45aaba61990"; } 
                                attribute :>> isControl = false; 
                                attribute :>> isControlType = false; 
                                attribute :>> kindOfNode = ObjectNodeKind::Unspecified; 
                                attribute :>> ordering = ObjectNodeOrderingKind::FIFO; 
                            }  
                            in port 'FIP 2' : FunctionInputPort  { 
                                @CapellaID { eid = "753f6bc9-9ff6-4278-a73f-e35cbaccdc6b"; } 
                                attribute :>> isControl = false; 
                                attribute :>> isControlType = false; 
                                attribute :>> kindOfNode = ObjectNodeKind::Unspecified; 
                                attribute :>> ordering = ObjectNodeOrderingKind::FIFO; 
                            }  
                            in port 'FIP 3' : FunctionInputPort  { 
                                @CapellaID { eid = "76b30bef-b1d0-42c5-b396-eed76dadace1"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'System Analysis'::'System Functions'::'Root System Function'.'Control temperature'.'Limit power'.'FOP 1'); 
                            ref :>> inputs =  ('eRod_Autonomous_Vehicle_2024 Project'::'eRod_Autonomous_Vehicle_2024'::'System Analysis'::'System Functions'::'Root System Function'.'Control temperature'.'Limit power'.'FIP 2',
                            'eRod_Autonomous_Vehicle_2024 Project'::'eRod_Autonomous_Vehicle_2024'::'System Analysis'::'System Functions'::'Root System Function'.'Control temperature'.'Limit power'.'FIP 3'); 
                        }  
                        interface '18057854-deb7-4fe3-b819-59ae67e7b705' : FunctionalExchange 
                            connect source ::> 'eRod_Autonomous_Vehicle_2024 Project'::'eRod_Autonomous_Vehicle_2024'::'System Analysis'::'System Functions'::'Root System Function'.'Control temperature'.'Limit temperature'.'FOP 1'
                            to target ::> 'eRod_Autonomous_Vehicle_2024 Project'::'eRod_Autonomous_Vehicle_2024'::'System Analysis'::'System Functions'::'Root System Function'.'Control temperature'.'Limit power'.'FIP 2' { 
                            @CapellaID { eid = "18057854-deb7-4fe3-b819-59ae67e7b705"; } 
                            attribute :>> isMulticast = false; 
                            attribute :>> isMultireceive = false; 
                            attribute :>> kindOfRate = RateKind::Unspecified; 
                            attribute :>> interfaceName = "Signal"; 
                        }  
                        ref :>> ownedFunctions =  ('eRod_Autonomous_Vehicle_2024 Project'::'eRod_Autonomous_Vehicle_2024'::'System Analysis'::'System Functions'::'Root System Function'.'Control temperature'.'Limit temperature',
                        'eRod_Autonomous_Vehicle_2024 Project'::'eRod_Autonomous_Vehicle_2024'::'System Analysis'::'System Functions'::'Root System Function'.'Control temperature'.'Limit power'); 
                        ref :>> ownedFunctionalExchanges =  ('eRod_Autonomous_Vehicle_2024 Project'::'eRod_Autonomous_Vehicle_2024'::'System Analysis'::'System Functions'::'Root System Function'.'Control temperature'.'18057854-deb7-4fe3-b819-59ae67e7b705'); 
                    }  
                    action 'Recieve feedback' : SystemFunction  { 
                        @CapellaID { eid = "5e70425b-121b-4c11-bcf5-fb75be1bddfd"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outSolve' : FunctionOutputPort  { 
                            @CapellaID { eid = "b9846e6c-14b0-438d-a8d2-c6b19107129b"; } 
                            attribute :>> isControl = false; 
                            attribute :>> isControlType = false; 
                            attribute :>> kindOfNode = ObjectNodeKind::Unspecified; 
                            attribute :>> ordering = ObjectNodeOrderingKind::FIFO; 
                        }  
                        in port 'inFeedback' : FunctionInputPort  { 
                            @CapellaID { eid = "d9090631-2f8e-4439-94e3-1d430e67aec4"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Recieve feedback'.'outSolve'); 
                        ref :>> inputs =  ('eRod_Autonomous_Vehicle_2024 Project'::'eRod_Autonomous_Vehicle_2024'::'System Analysis'::'System Functions'::'Root System Function'.'Recieve feedback'.'inFeedback'); 
                    }  
                    action 'Provide solution' : SystemFunction  { 
                        @CapellaID { eid = "76e1cf30-4aa6-4118-8ce4-0beb1e37970b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outUpdate' : FunctionOutputPort  { 
                            @CapellaID { eid = "069c0b45-0834-4519-8f4c-2585099d85fa"; } 
                            attribute :>> isControl = false; 
                            attribute :>> isControlType = false; 
                            attribute :>> kindOfNode = ObjectNodeKind::Unspecified; 
                            attribute :>> ordering = ObjectNodeOrderingKind::FIFO; 
                        }  
                        out port 'FOP 2' : FunctionOutputPort  { 
                            @CapellaID { eid = "23dbd724-934e-4e5a-9367-8f0eddf24752"; } 
                            attribute :>> isControl = false; 
                            attribute :>> isControlType = false; 
                            attribute :>> kindOfNode = ObjectNodeKind::Unspecified; 
                            attribute :>> ordering = ObjectNodeOrderingKind::FIFO; 
                        }  
                        in port 'inSolve' : FunctionInputPort  { 
                            @CapellaID { eid = "25bf5a8f-cb24-43fc-b17f-14e4e77d877e"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Provide solution'.'outUpdate',
                        'eRod_Autonomous_Vehicle_2024 Project'::'eRod_Autonomous_Vehicle_2024'::'System Analysis'::'System Functions'::'Root System Function'.'Provide solution'.'FOP 2'); 
                        ref :>> inputs =  ('eRod_Autonomous_Vehicle_2024 Project'::'eRod_Autonomous_Vehicle_2024'::'System Analysis'::'System Functions'::'Root System Function'.'Provide solution'.'inSolve'); 
                    }  
                    action 'Informed Software update' : SystemFunction  { 
                        @CapellaID { eid = "caee452f-fd53-48c1-8c72-5a5f0cd32e07"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outApproval' : FunctionOutputPort  { 
                            @CapellaID { eid = "0473cccf-d460-4273-bc8e-6dcb0f0b47fb"; } 
                            attribute :>> isControl = false; 
                            attribute :>> isControlType = false; 
                            attribute :>> kindOfNode = ObjectNodeKind::Unspecified; 
                            attribute :>> ordering = ObjectNodeOrderingKind::FIFO; 
                        }  
                        in port 'inUpdate' : FunctionInputPort  { 
                            @CapellaID { eid = "bf11d109-e48f-4864-8949-eb9a16058ce4"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Informed Software update'.'outApproval'); 
                        ref :>> inputs =  ('eRod_Autonomous_Vehicle_2024 Project'::'eRod_Autonomous_Vehicle_2024'::'System Analysis'::'System Functions'::'Root System Function'.'Informed Software update'.'inUpdate'); 
                    }  
                    action 'Status and command indication' : SystemFunction  { 
                        @CapellaID { eid = "2e1a6726-aaac-461c-a8f3-e60658cb1418"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outRequest parking' : FunctionOutputPort  { 
                            @CapellaID { eid = "064c55c5-9f31-4db1-9b3f-f806e84978a6"; } 
                            attribute :>> isControl = false; 
                            attribute :>> isControlType = false; 
                            attribute :>> kindOfNode = ObjectNodeKind::Unspecified; 
                            attribute :>> ordering = ObjectNodeOrderingKind::FIFO; 
                        }  
                        out port 'outParking Status' : FunctionOutputPort  { 
                            @CapellaID { eid = "0b370d80-6d26-4b0d-af7b-ab5ac2c30904"; } 
                            attribute :>> isControl = false; 
                            attribute :>> isControlType = false; 
                            attribute :>> kindOfNode = ObjectNodeKind::Unspecified; 
                            attribute :>> ordering = ObjectNodeOrderingKind::FIFO; 
                        }  
                        in port 'inActivate' : FunctionInputPort  { 
                            @CapellaID { eid = "7103123a-dfff-4099-a05f-0f770cb3ba92"; } 
                            attribute :>> isControl = false; 
                            attribute :>> isControlType = false; 
                            attribute :>> kindOfNode = ObjectNodeKind::Unspecified; 
                            attribute :>> ordering = ObjectNodeOrderingKind::FIFO; 
                        }  
                        in port 'inDeactivate' : FunctionInputPort  { 
                            @CapellaID { eid = "50abb025-2b65-40ed-b20d-e06c622172bd"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Status and command indication'.'outRequest parking',
                        'eRod_Autonomous_Vehicle_2024 Project'::'eRod_Autonomous_Vehicle_2024'::'System Analysis'::'System Functions'::'Root System Function'.'Status and command indication'.'outParking Status'); 
                        ref :>> inputs =  ('eRod_Autonomous_Vehicle_2024 Project'::'eRod_Autonomous_Vehicle_2024'::'System Analysis'::'System Functions'::'Root System Function'.'Status and command indication'.'inActivate',
                        'eRod_Autonomous_Vehicle_2024 Project'::'eRod_Autonomous_Vehicle_2024'::'System Analysis'::'System Functions'::'Root System Function'.'Status and command indication'.'inDeactivate'); 
                    }  
                    action 'Maintain distance' : SystemFunction  { 
                        @CapellaID { eid = "12fa82d8-c489-464f-a64a-7bf205135eca"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "5f7dc02e-6596-4f85-a4d8-deaff9ce94e3"; } 
                            attribute :>> isControl = false; 
                            attribute :>> isControlType = false; 
                            attribute :>> kindOfNode = ObjectNodeKind::Unspecified; 
                            attribute :>> ordering = ObjectNodeOrderingKind::FIFO; 
                        }  
                        out port 'FOP 2' : FunctionOutputPort  { 
                            @CapellaID { eid = "b2bd6ad5-921e-4ab7-9c96-6262275c81d4"; } 
                            attribute :>> isControl = false; 
                            attribute :>> isControlType = false; 
                            attribute :>> kindOfNode = ObjectNodeKind::Unspecified; 
                            attribute :>> ordering = ObjectNodeOrderingKind::FIFO; 
                        }  
                        out port 'FOP 3' : FunctionOutputPort  { 
                            @CapellaID { eid = "7b7ac2c6-9f40-4000-87db-a52ded69b243"; } 
                            attribute :>> isControl = false; 
                            attribute :>> isControlType = false; 
                            attribute :>> kindOfNode = ObjectNodeKind::Unspecified; 
                            attribute :>> ordering = ObjectNodeOrderingKind::FIFO; 
                        }  
                        out port 'outActive braking' : FunctionOutputPort  { 
                            @CapellaID { eid = "e227ac3b-05f7-42a5-b151-5368bbf95071"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "0ea4d926-e629-481b-bf9b-7e1049754614"; } 
                            attribute :>> isControl = false; 
                            attribute :>> isControlType = false; 
                            attribute :>> kindOfNode = ObjectNodeKind::Unspecified; 
                            attribute :>> ordering = ObjectNodeOrderingKind::FIFO; 
                        }  
                        in port 'FIP 2' : FunctionInputPort  { 
                            @CapellaID { eid = "908d605a-7d18-41b7-b390-790fe5a3790a"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Maintain distance'.'FOP 1',
                        'eRod_Autonomous_Vehicle_2024 Project'::'eRod_Autonomous_Vehicle_2024'::'System Analysis'::'System Functions'::'Root System Function'.'Maintain distance'.'FOP 2',
                        'eRod_Autonomous_Vehicle_2024 Project'::'eRod_Autonomous_Vehicle_2024'::'System Analysis'::'System Functions'::'Root System Function'.'Maintain distance'.'FOP 3',
                        'eRod_Autonomous_Vehicle_2024 Project'::'eRod_Autonomous_Vehicle_2024'::'System Analysis'::'System Functions'::'Root System Function'.'Maintain distance'.'outActive braking'); 
                        ref :>> inputs =  ('eRod_Autonomous_Vehicle_2024 Project'::'eRod_Autonomous_Vehicle_2024'::'System Analysis'::'System Functions'::'Root System Function'.'Maintain distance'.'FIP 1',
                        'eRod_Autonomous_Vehicle_2024 Project'::'eRod_Autonomous_Vehicle_2024'::'System Analysis'::'System Functions'::'Root System Function'.'Maintain distance'.'FIP 2'); 
                    }  
                    action 'Steer Wheels Remote' : SystemFunction  { 
                        @CapellaID { eid = "d742198e-ecb9-46e6-8565-750cb0d82968"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outWheel Position' : FunctionOutputPort  { 
                            @CapellaID { eid = "f43bb2bd-5f24-46e2-a56c-9bd3d7bcc1e2"; } 
                            attribute :>> isControl = false; 
                            attribute :>> isControlType = false; 
                            attribute :>> kindOfNode = ObjectNodeKind::Unspecified; 
                            attribute :>> ordering = ObjectNodeOrderingKind::FIFO; 
                        }  
                        in port 'inSteering Commands' : FunctionInputPort  { 
                            @CapellaID { eid = "0d6345f6-13c7-4d01-93c7-2026b16486f5"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Steer Wheels Remote'.'outWheel Position'); 
                        ref :>> inputs =  ('eRod_Autonomous_Vehicle_2024 Project'::'eRod_Autonomous_Vehicle_2024'::'System Analysis'::'System Functions'::'Root System Function'.'Steer Wheels Remote'.'inSteering Commands'); 
                    }  
                    action 'Control braking' : SystemFunction  { 
                        @CapellaID { eid = "1dafdd86-8815-4676-8c74-8bad155ecd63"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "e9a330cb-9f4e-4852-aa2d-dbb350f4d320"; } 
                            attribute :>> isControl = false; 
                            attribute :>> isControlType = false; 
                            attribute :>> kindOfNode = ObjectNodeKind::Unspecified; 
                            attribute :>> ordering = ObjectNodeOrderingKind::FIFO; 
                        }  
                        out port 'outDeceleration' : FunctionOutputPort  { 
                            @CapellaID { eid = "8970d7f5-e9ec-424e-8cbe-4dbbaed218b7"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "8d5465af-253c-4d81-876d-ba44ba1fbd5b"; } 
                            attribute :>> isControl = false; 
                            attribute :>> isControlType = false; 
                            attribute :>> kindOfNode = ObjectNodeKind::Unspecified; 
                            attribute :>> ordering = ObjectNodeOrderingKind::FIFO; 
                        }  
                        in port 'FIP 2' : FunctionInputPort  { 
                            @CapellaID { eid = "3b256fdf-40d6-43e4-a677-1caee057cc2d"; } 
                            attribute :>> isControl = false; 
                            attribute :>> isControlType = false; 
                            attribute :>> kindOfNode = ObjectNodeKind::Unspecified; 
                            attribute :>> ordering = ObjectNodeOrderingKind::FIFO; 
                        }  
                        in port 'FIP 3' : FunctionInputPort  { 
                            @CapellaID { eid = "df740422-f7eb-4ff8-84fa-b3d50fa4529b"; } 
                            attribute :>> isControl = false; 
                            attribute :>> isControlType = false; 
                            attribute :>> kindOfNode = ObjectNodeKind::Unspecified; 
                            attribute :>> ordering = ObjectNodeOrderingKind::FIFO; 
                        }  
                        in port 'FIP 4' : FunctionInputPort  { 
                            @CapellaID { eid = "3c222081-970e-46c7-bfd6-23e0ecad1e4e"; } 
                            attribute :>> isControl = false; 
                            attribute :>> isControlType = false; 
                            attribute :>> kindOfNode = ObjectNodeKind::Unspecified; 
                            attribute :>> ordering = ObjectNodeOrderingKind::FIFO; 
                        }  
                        in port 'inActive braking' : FunctionInputPort  { 
                            @CapellaID { eid = "d7bfaa82-ee4b-4840-99c8-22eb35c32646"; } 
                            attribute :>> isControl = false; 
                            attribute :>> isControlType = false; 
                            attribute :>> kindOfNode = ObjectNodeKind::Unspecified; 
                            attribute :>> ordering = ObjectNodeOrderingKind::FIFO; 
                        }  
                        in port 'inBraking Commands' : FunctionInputPort  { 
                            @CapellaID { eid = "6fb897d2-3902-4b12-a0de-a83df1b0f8d2"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Control braking'.'FOP 1',
                        'eRod_Autonomous_Vehicle_2024 Project'::'eRod_Autonomous_Vehicle_2024'::'System Analysis'::'System Functions'::'Root System Function'.'Control braking'.'outDeceleration'); 
                        ref :>> inputs =  ('eRod_Autonomous_Vehicle_2024 Project'::'eRod_Autonomous_Vehicle_2024'::'System Analysis'::'System Functions'::'Root System Function'.'Control braking'.'FIP 1',
                        'eRod_Autonomous_Vehicle_2024 Project'::'eRod_Autonomous_Vehicle_2024'::'System Analysis'::'System Functions'::'Root System Function'.'Control braking'.'FIP 2',
                        'eRod_Autonomous_Vehicle_2024 Project'::'eRod_Autonomous_Vehicle_2024'::'System Analysis'::'System Functions'::'Root System Function'.'Control braking'.'FIP 3',
                        'eRod_Autonomous_Vehicle_2024 Project'::'eRod_Autonomous_Vehicle_2024'::'System Analysis'::'System Functions'::'Root System Function'.'Control braking'.'FIP 4',
                        'eRod_Autonomous_Vehicle_2024 Project'::'eRod_Autonomous_Vehicle_2024'::'System Analysis'::'System Functions'::'Root System Function'.'Control braking'.'inActive braking',
                        'eRod_Autonomous_Vehicle_2024 Project'::'eRod_Autonomous_Vehicle_2024'::'System Analysis'::'System Functions'::'Root System Function'.'Control braking'.'inBraking Commands'); 
                    }  
                    action 'Locate targets' : SystemFunction  { 
                        @CapellaID { eid = "cc0945cb-9c94-4076-b3ea-cf2dbf9814b8"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "d77ad8d9-e6b3-4791-94af-858dc7f9fa30"; } 
                            attribute :>> isControl = false; 
                            attribute :>> isControlType = false; 
                            attribute :>> kindOfNode = ObjectNodeKind::Unspecified; 
                            attribute :>> ordering = ObjectNodeOrderingKind::FIFO; 
                        }  
                        out port 'FOP 2' : FunctionOutputPort  { 
                            @CapellaID { eid = "2cbd7a6f-c8c7-4af9-80f0-1710aae37959"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "e9979b8a-a709-4f3f-b13d-3fcee46dcd59"; } 
                            attribute :>> isControl = false; 
                            attribute :>> isControlType = false; 
                            attribute :>> kindOfNode = ObjectNodeKind::Unspecified; 
                            attribute :>> ordering = ObjectNodeOrderingKind::FIFO; 
                        }  
                        in port 'FIP 2' : FunctionInputPort  { 
                            @CapellaID { eid = "ff1ae4c8-6538-4889-aa94-85e9e9bc7ae8"; } 
                            attribute :>> isControl = false; 
                            attribute :>> isControlType = false; 
                            attribute :>> kindOfNode = ObjectNodeKind::Unspecified; 
                            attribute :>> ordering = ObjectNodeOrderingKind::FIFO; 
                        }  
                        in port 'FIP 3' : FunctionInputPort  { 
                            @CapellaID { eid = "1d222810-6a5f-4de6-beb0-a260c64c3935"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Locate targets'.'FOP 1',
                        'eRod_Autonomous_Vehicle_2024 Project'::'eRod_Autonomous_Vehicle_2024'::'System Analysis'::'System Functions'::'Root System Function'.'Locate targets'.'FOP 2'); 
                        ref :>> inputs =  ('eRod_Autonomous_Vehicle_2024 Project'::'eRod_Autonomous_Vehicle_2024'::'System Analysis'::'System Functions'::'Root System Function'.'Locate targets'.'FIP 1',
                        'eRod_Autonomous_Vehicle_2024 Project'::'eRod_Autonomous_Vehicle_2024'::'System Analysis'::'System Functions'::'Root System Function'.'Locate targets'.'FIP 2',
                        'eRod_Autonomous_Vehicle_2024 Project'::'eRod_Autonomous_Vehicle_2024'::'System Analysis'::'System Functions'::'Root System Function'.'Locate targets'.'FIP 3'); 
                    }  
                    action 'Maintain speed' : SystemFunction  { 
                        @CapellaID { eid = "50727822-39df-4b3b-b47d-457dfe24274c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "0536292a-2e1f-4785-832c-bfeec9e8904d"; } 
                            attribute :>> isControl = false; 
                            attribute :>> isControlType = false; 
                            attribute :>> kindOfNode = ObjectNodeKind::Unspecified; 
                            attribute :>> ordering = ObjectNodeOrderingKind::FIFO; 
                        }  
                        in port 'FIP 2' : FunctionInputPort  { 
                            @CapellaID { eid = "81a50dee-2b17-4780-8885-89556634ef1a"; } 
                            attribute :>> isControl = false; 
                            attribute :>> isControlType = false; 
                            attribute :>> kindOfNode = ObjectNodeKind::Unspecified; 
                            attribute :>> ordering = ObjectNodeOrderingKind::FIFO; 
                        }  
                        ref :>> inputs =  ('eRod_Autonomous_Vehicle_2024 Project'::'eRod_Autonomous_Vehicle_2024'::'System Analysis'::'System Functions'::'Root System Function'.'Maintain speed'.'FIP 1',
                        'eRod_Autonomous_Vehicle_2024 Project'::'eRod_Autonomous_Vehicle_2024'::'System Analysis'::'System Functions'::'Root System Function'.'Maintain speed'.'FIP 2'); 
                    }  
                    action 'Drive vehicle' : SystemFunction  { 
                        @CapellaID { eid = "45abe338-a182-4c88-ad8e-d6de9b36ebd3"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "03fc2a02-192c-495b-a5f0-26c2ac652f02"; } 
                            attribute :>> isControl = false; 
                            attribute :>> isControlType = false; 
                            attribute :>> kindOfNode = ObjectNodeKind::Unspecified; 
                            attribute :>> ordering = ObjectNodeOrderingKind::FIFO; 
                        }  
                        out port 'FOP 2' : FunctionOutputPort  { 
                            @CapellaID { eid = "76c4b0cf-c89e-4a6d-8015-eaf1332884ef"; } 
                            attribute :>> isControl = false; 
                            attribute :>> isControlType = false; 
                            attribute :>> kindOfNode = ObjectNodeKind::Unspecified; 
                            attribute :>> ordering = ObjectNodeOrderingKind::FIFO; 
                        }  
                        out port 'FOP 3' : FunctionOutputPort  { 
                            @CapellaID { eid = "fb03cf01-581a-436a-94cc-b9e3f7a960a7"; } 
                            attribute :>> isControl = false; 
                            attribute :>> isControlType = false; 
                            attribute :>> kindOfNode = ObjectNodeKind::Unspecified; 
                            attribute :>> ordering = ObjectNodeOrderingKind::FIFO; 
                        }  
                        out port 'outLocation' : FunctionOutputPort  { 
                            @CapellaID { eid = "d37ec55d-311c-4b3e-9c3a-666d493fb887"; } 
                            attribute :>> isControl = false; 
                            attribute :>> isControlType = false; 
                            attribute :>> kindOfNode = ObjectNodeKind::Unspecified; 
                            attribute :>> ordering = ObjectNodeOrderingKind::FIFO; 
                        }  
                        in port 'inTerrain' : FunctionInputPort  { 
                            @CapellaID { eid = "7b82380c-7832-4cfc-97fa-6704e919a59e"; } 
                            attribute :>> isControl = false; 
                            attribute :>> isControlType = false; 
                            attribute :>> kindOfNode = ObjectNodeKind::Unspecified; 
                            attribute :>> ordering = ObjectNodeOrderingKind::FIFO; 
                        }  
                        in port 'inObjects' : FunctionInputPort  { 
                            @CapellaID { eid = "e16bf77f-47ab-4a15-b6ea-81134de34d04"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Drive vehicle'.'FOP 1',
                        'eRod_Autonomous_Vehicle_2024 Project'::'eRod_Autonomous_Vehicle_2024'::'System Analysis'::'System Functions'::'Root System Function'.'Drive vehicle'.'FOP 2',
                        'eRod_Autonomous_Vehicle_2024 Project'::'eRod_Autonomous_Vehicle_2024'::'System Analysis'::'System Functions'::'Root System Function'.'Drive vehicle'.'FOP 3',
                        'eRod_Autonomous_Vehicle_2024 Project'::'eRod_Autonomous_Vehicle_2024'::'System Analysis'::'System Functions'::'Root System Function'.'Drive vehicle'.'outLocation'); 
                        ref :>> inputs =  ('eRod_Autonomous_Vehicle_2024 Project'::'eRod_Autonomous_Vehicle_2024'::'System Analysis'::'System Functions'::'Root System Function'.'Drive vehicle'.'inTerrain',
                        'eRod_Autonomous_Vehicle_2024 Project'::'eRod_Autonomous_Vehicle_2024'::'System Analysis'::'System Functions'::'Root System Function'.'Drive vehicle'.'inObjects'); 
                    }  
                    action 'Park vehicle' : SystemFunction  { 
                        @CapellaID { eid = "56ddee16-68a9-4948-bbd7-249f68ca3ade"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outBraking Commands' : FunctionOutputPort  { 
                            @CapellaID { eid = "a59e9e2e-6482-4dcb-80dc-62dcffd9e83d"; } 
                            attribute :>> isControl = false; 
                            attribute :>> isControlType = false; 
                            attribute :>> kindOfNode = ObjectNodeKind::Unspecified; 
                            attribute :>> ordering = ObjectNodeOrderingKind::FIFO; 
                        }  
                        out port 'outSteering Commands' : FunctionOutputPort  { 
                            @CapellaID { eid = "3cee7199-c720-47f3-81af-44ea81b46ed1"; } 
                            attribute :>> isControl = false; 
                            attribute :>> isControlType = false; 
                            attribute :>> kindOfNode = ObjectNodeKind::Unspecified; 
                            attribute :>> ordering = ObjectNodeOrderingKind::FIFO; 
                        }  
                        in port 'inRequest parking' : FunctionInputPort  { 
                            @CapellaID { eid = "164de631-31c6-4281-af70-8ce62c3b714f"; } 
                            attribute :>> isControl = false; 
                            attribute :>> isControlType = false; 
                            attribute :>> kindOfNode = ObjectNodeKind::Unspecified; 
                            attribute :>> ordering = ObjectNodeOrderingKind::FIFO; 
                        }  
                        in port 'inInitiate Park' : FunctionInputPort  { 
                            @CapellaID { eid = "b2c6f731-381c-415c-843f-fd6e98dfbde6"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Park vehicle'.'outBraking Commands',
                        'eRod_Autonomous_Vehicle_2024 Project'::'eRod_Autonomous_Vehicle_2024'::'System Analysis'::'System Functions'::'Root System Function'.'Park vehicle'.'outSteering Commands'); 
                        ref :>> inputs =  ('eRod_Autonomous_Vehicle_2024 Project'::'eRod_Autonomous_Vehicle_2024'::'System Analysis'::'System Functions'::'Root System Function'.'Park vehicle'.'inRequest parking',
                        'eRod_Autonomous_Vehicle_2024 Project'::'eRod_Autonomous_Vehicle_2024'::'System Analysis'::'System Functions'::'Root System Function'.'Park vehicle'.'inInitiate Park'); 
                    }  
                    action 'Vehicle Command' : SystemFunction  { 
                        @CapellaID { eid = "fa17a1ea-c8fc-4d98-b20d-d20b8360ef8b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outVehicle Commands' : FunctionOutputPort  { 
                            @CapellaID { eid = "fdff8726-c17d-4ac4-ad21-9301fa55ab00"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Vehicle Command'.'outVehicle Commands'); 
                    }  
                    action 'Remote Operate Car' : SystemFunction  { 
                        @CapellaID { eid = "0cc1204a-6fa5-4d45-b0e8-c13a55b0ffc0"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outInitiate Park' : FunctionOutputPort  { 
                            @CapellaID { eid = "7a64625b-7b5d-4a3a-9004-e0b3220f47a7"; } 
                            attribute :>> isControl = false; 
                            attribute :>> isControlType = false; 
                            attribute :>> kindOfNode = ObjectNodeKind::Unspecified; 
                            attribute :>> ordering = ObjectNodeOrderingKind::FIFO; 
                        }  
                        in port 'inVehicle Commands' : FunctionInputPort  { 
                            @CapellaID { eid = "113d501b-4028-4fc1-abfa-6450d689e39f"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Remote Operate Car'.'outInitiate Park'); 
                        ref :>> inputs =  ('eRod_Autonomous_Vehicle_2024 Project'::'eRod_Autonomous_Vehicle_2024'::'System Analysis'::'System Functions'::'Root System Function'.'Remote Operate Car'.'inVehicle Commands'); 
                    }  
                    action 'Avoid collision' : SystemFunction  { 
                        @CapellaID { eid = "aacc0b49-3cc6-41c3-bd63-1080fb5da920"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "ca935642-a0bb-43e2-9b5d-4b39c4e71eeb"; } 
                            attribute :>> isControl = false; 
                            attribute :>> isControlType = false; 
                            attribute :>> kindOfNode = ObjectNodeKind::Unspecified; 
                            attribute :>> ordering = ObjectNodeOrderingKind::FIFO; 
                        }  
                        out port 'FOP 2' : FunctionOutputPort  { 
                            @CapellaID { eid = "166d6ca9-af9d-4746-8a3d-61217e64b715"; } 
                            attribute :>> isControl = false; 
                            attribute :>> isControlType = false; 
                            attribute :>> kindOfNode = ObjectNodeKind::Unspecified; 
                            attribute :>> ordering = ObjectNodeOrderingKind::FIFO; 
                        }  
                        out port 'FOP 3' : FunctionOutputPort  { 
                            @CapellaID { eid = "80082531-852a-496a-b37f-cb9211a260cd"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "17232627-3944-4b5e-a820-683f1441246f"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Avoid collision'.'FOP 1',
                        'eRod_Autonomous_Vehicle_2024 Project'::'eRod_Autonomous_Vehicle_2024'::'System Analysis'::'System Functions'::'Root System Function'.'Avoid collision'.'FOP 2',
                        'eRod_Autonomous_Vehicle_2024 Project'::'eRod_Autonomous_Vehicle_2024'::'System Analysis'::'System Functions'::'Root System Function'.'Avoid collision'.'FOP 3'); 
                        ref :>> inputs =  ('eRod_Autonomous_Vehicle_2024 Project'::'eRod_Autonomous_Vehicle_2024'::'System Analysis'::'System Functions'::'Root System Function'.'Avoid collision'.'FIP 1'); 
                    }  
                    action 'Provide object location' : SystemFunction  { 
                        @CapellaID { eid = "b80325da-ff39-4e1c-be4c-07e42402cbca"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "2b48a42d-451d-403a-ad05-e0f350558ab3"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'System Analysis'::'System Functions'::'Root System Function'.'Provide object location'.'FOP 1'); 
                    }  
                    action 'Observe status' : SystemFunction  { 
                        @CapellaID { eid = "80660eda-35b4-47f3-ab76-b812bfb08b6f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "4a05e452-17ac-4c10-b286-8c3abc7fa8e0"; } 
                            attribute :>> isControl = false; 
                            attribute :>> isControlType = false; 
                            attribute :>> kindOfNode = ObjectNodeKind::Unspecified; 
                            attribute :>> ordering = ObjectNodeOrderingKind::FIFO; 
                        }  
                         
                        ref :>> inputs =  ('eRod_Autonomous_Vehicle_2024 Project'::'eRod_Autonomous_Vehicle_2024'::'System Analysis'::'System Functions'::'Root System Function'.'Observe status'.'FIP 1'); 
                    }  
                    action 'Provide vehicle status' : SystemFunction  { 
                        @CapellaID { eid = "3efd825f-b90f-4600-96ca-49ce979751d4"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "95f7bd38-3a96-4a98-b8c5-26f747f23b7d"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "413ec5c3-bd6c-4f06-a6e5-ca82141b793f"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Provide vehicle status'.'FOP 1'); 
                        ref :>> inputs =  ('eRod_Autonomous_Vehicle_2024 Project'::'eRod_Autonomous_Vehicle_2024'::'System Analysis'::'System Functions'::'Root System Function'.'Provide vehicle status'.'FIP 1'); 
                    }  
                    action 'Steer wheels' : SystemFunction  { 
                        @CapellaID { eid = "9cfb818b-1416-4579-a617-2a17313b9be7"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "bd3f573e-3f52-4ff8-b8fc-d7af14c65390"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "c1fc4ae4-ed43-4bc8-a9d5-e48e7b5c8fea"; } 
                            attribute :>> isControl = false; 
                            attribute :>> isControlType = false; 
                            attribute :>> kindOfNode = ObjectNodeKind::Unspecified; 
                            attribute :>> ordering = ObjectNodeOrderingKind::FIFO; 
                        }  
                        in port 'FIP 2' : FunctionInputPort  { 
                            @CapellaID { eid = "51c255e7-79da-421e-8702-901b572d9af2"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'System Analysis'::'System Functions'::'Root System Function'.'Steer wheels'.'FOP 1'); 
                        ref :>> inputs =  ('eRod_Autonomous_Vehicle_2024 Project'::'eRod_Autonomous_Vehicle_2024'::'System Analysis'::'System Functions'::'Root System Function'.'Steer wheels'.'FIP 1',
                        'eRod_Autonomous_Vehicle_2024 Project'::'eRod_Autonomous_Vehicle_2024'::'System Analysis'::'System Functions'::'Root System Function'.'Steer wheels'.'FIP 2'); 
                    }  
                    action 'Automatic Steering' : SystemFunction  { 
                        @CapellaID { eid = "7ab1ee80-0487-4dc3-9df7-0c01307f32d0"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "766e0377-60aa-475c-8916-3abb35da2240"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "ab934165-6ae0-42ec-b190-52c49a74e4ef"; } 
                            attribute :>> isControl = false; 
                            attribute :>> isControlType = false; 
                            attribute :>> kindOfNode = ObjectNodeKind::Unspecified; 
                            attribute :>> ordering = ObjectNodeOrderingKind::FIFO; 
                        }  
                        in port 'FIP 2' : FunctionInputPort  { 
                            @CapellaID { eid = "94e627d0-637c-430b-9ef7-b8629e03dd71"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'System Analysis'::'System Functions'::'Root System Function'.'Automatic Steering'.'FOP 1'); 
                        ref :>> inputs =  ('eRod_Autonomous_Vehicle_2024 Project'::'eRod_Autonomous_Vehicle_2024'::'System Analysis'::'System Functions'::'Root System Function'.'Automatic Steering'.'FIP 1',
                        'eRod_Autonomous_Vehicle_2024 Project'::'eRod_Autonomous_Vehicle_2024'::'System Analysis'::'System Functions'::'Root System Function'.'Automatic Steering'.'FIP 2'); 
                    }  
                    action 'Detect road' : SystemFunction  { 
                        @CapellaID { eid = "8f5e7828-1314-42ef-bede-95f1f77950f3"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "30163868-2444-4673-8768-172334675b93"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "d799f03b-e876-4a72-9338-e22f0e4102dc"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'System Analysis'::'System Functions'::'Root System Function'.'Detect road'.'FOP 1'); 
                        ref :>> inputs =  ('eRod_Autonomous_Vehicle_2024 Project'::'eRod_Autonomous_Vehicle_2024'::'System Analysis'::'System Functions'::'Root System Function'.'Detect road'.'FIP 1'); 
                    }  
                    action 'Provide road markers' : SystemFunction  { 
                        @CapellaID { eid = "9e6c9717-45c2-4134-9e4c-8e3ba67be129"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "7ccf479f-3e55-4988-bc29-d726d0d2411a"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'System Analysis'::'System Functions'::'Root System Function'.'Provide road markers'.'FOP 1'); 
                    }  
                    action 'Provide target vehicle velocity' : SystemFunction  { 
                        @CapellaID { eid = "609e4ae2-dbe0-41ac-8e4c-2523ff0e529a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "edb9abdd-f614-4b37-b54e-a6c258370667"; } 
                            attribute :>> isControl = false; 
                            attribute :>> isControlType = false; 
                            attribute :>> kindOfNode = ObjectNodeKind::Unspecified; 
                            attribute :>> ordering = ObjectNodeOrderingKind::FIFO; 
                        }  
                        out port 'FOP 2' : FunctionOutputPort  { 
                            @CapellaID { eid = "7981f90f-c54b-464e-8dd7-0ec0ba4a4895"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'System Analysis'::'System Functions'::'Root System Function'.'Provide target vehicle velocity'.'FOP 1',
                        'eRod_Autonomous_Vehicle_2024 Project'::'eRod_Autonomous_Vehicle_2024'::'System Analysis'::'System Functions'::'Root System Function'.'Provide target vehicle velocity'.'FOP 2'); 
                    }  
                    action 'Provide diverse terrain' : SystemFunction  { 
                        @CapellaID { eid = "a7de5a7c-6dac-4308-9ee3-7cc6d3c7ce6b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outTerrain' : FunctionOutputPort  { 
                            @CapellaID { eid = "3d98d69c-31e9-4ecb-afba-2f00bc274c7b"; } 
                            attribute :>> isControl = false; 
                            attribute :>> isControlType = false; 
                            attribute :>> kindOfNode = ObjectNodeKind::Unspecified; 
                            attribute :>> ordering = ObjectNodeOrderingKind::FIFO; 
                        }  
                        in port 'inWeather' : FunctionInputPort  { 
                            @CapellaID { eid = "9b740456-4ac6-4fbb-9ee9-2095d5cfcfe0"; } 
                            attribute :>> isControl = false; 
                            attribute :>> isControlType = false; 
                            attribute :>> kindOfNode = ObjectNodeKind::Unspecified; 
                            attribute :>> ordering = ObjectNodeOrderingKind::FIFO; 
                        }  
                        in port 'inLocation' : FunctionInputPort  { 
                            @CapellaID { eid = "e8abdc89-ebff-48b4-8733-e2abfb527514"; } 
                            attribute :>> isControl = false; 
                            attribute :>> isControlType = false; 
                            attribute :>> kindOfNode = ObjectNodeKind::Unspecified; 
                            attribute :>> ordering = ObjectNodeOrderingKind::FIFO; 
                        }  
                        in port 'inTraction' : FunctionInputPort  { 
                            @CapellaID { eid = "d10ade20-ce43-4a44-a254-311bcd4fa363"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Provide diverse terrain'.'outTerrain'); 
                        ref :>> inputs =  ('eRod_Autonomous_Vehicle_2024 Project'::'eRod_Autonomous_Vehicle_2024'::'System Analysis'::'System Functions'::'Root System Function'.'Provide diverse terrain'.'inWeather',
                        'eRod_Autonomous_Vehicle_2024 Project'::'eRod_Autonomous_Vehicle_2024'::'System Analysis'::'System Functions'::'Root System Function'.'Provide diverse terrain'.'inLocation',
                        'eRod_Autonomous_Vehicle_2024 Project'::'eRod_Autonomous_Vehicle_2024'::'System Analysis'::'System Functions'::'Root System Function'.'Provide diverse terrain'.'inTraction'); 
                    }  
                    action 'Provide parking location' : SystemFunction  { 
                        @CapellaID { eid = "1ba3a370-1731-4497-bf0c-304ec833b1af"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                         
                    }  
                    action 'Activate Park Assist' : SystemFunction  { 
                        @CapellaID { eid = "b8de21f9-d39f-489b-a57f-f8ca022104a1"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outActivate' : FunctionOutputPort  { 
                            @CapellaID { eid = "4595a18e-1118-4cbe-ae6a-f83b5e71099d"; } 
                            attribute :>> isControl = false; 
                            attribute :>> isControlType = false; 
                            attribute :>> kindOfNode = ObjectNodeKind::Unspecified; 
                            attribute :>> ordering = ObjectNodeOrderingKind::FIFO; 
                        }  
                        out port 'outDeactivate' : FunctionOutputPort  { 
                            @CapellaID { eid = "e0a433d2-a6db-40df-a3f7-d65e657c104c"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Activate Park Assist'.'outActivate',
                        'eRod_Autonomous_Vehicle_2024 Project'::'eRod_Autonomous_Vehicle_2024'::'System Analysis'::'System Functions'::'Root System Function'.'Activate Park Assist'.'outDeactivate'); 
                    }  
                    action 'Deliver traction to surface' : SystemFunction  { 
                        @CapellaID { eid = "602dbf04-17f7-4e01-8bc0-7f8cdde4e71c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outTraction' : FunctionOutputPort  { 
                            @CapellaID { eid = "97b2ec9c-9518-4adc-b359-ce0e71a7689c"; } 
                            attribute :>> isControl = false; 
                            attribute :>> isControlType = false; 
                            attribute :>> kindOfNode = ObjectNodeKind::Unspecified; 
                            attribute :>> ordering = ObjectNodeOrderingKind::FIFO; 
                        }  
                        in port 'inDeceleration' : FunctionInputPort  { 
                            @CapellaID { eid = "52e648a9-8e3c-4a35-8838-0b14433abeaa"; } 
                            attribute :>> isControl = false; 
                            attribute :>> isControlType = false; 
                            attribute :>> kindOfNode = ObjectNodeKind::Unspecified; 
                            attribute :>> ordering = ObjectNodeOrderingKind::FIFO; 
                        }  
                        in port 'inWheel Position' : FunctionInputPort  { 
                            @CapellaID { eid = "75f1a4e7-37e8-4f8d-aac7-b709a0055026"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Deliver traction to surface'.'outTraction'); 
                        ref :>> inputs =  ('eRod_Autonomous_Vehicle_2024 Project'::'eRod_Autonomous_Vehicle_2024'::'System Analysis'::'System Functions'::'Root System Function'.'Deliver traction to surface'.'inDeceleration',
                        'eRod_Autonomous_Vehicle_2024 Project'::'eRod_Autonomous_Vehicle_2024'::'System Analysis'::'System Functions'::'Root System Function'.'Deliver traction to surface'.'inWheel Position'); 
                    }  
                    action 'Provide weather' : SystemFunction  { 
                        @CapellaID { eid = "3907e586-8ab5-4500-b0f0-1d9036f43220"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outWeather' : FunctionOutputPort  { 
                            @CapellaID { eid = "bf68bf1b-87d6-4556-85aa-0325a0d16d12"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Provide weather'.'outWeather'); 
                    }  
                    action 'Move objects' : SystemFunction  { 
                        @CapellaID { eid = "ee47c40b-a4fd-40ec-96bf-043d00914934"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outObjects' : FunctionOutputPort  { 
                            @CapellaID { eid = "6f5ec561-f430-4626-a51c-0d4102a19760"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'System Analysis'::'System Functions'::'Root System Function'.'Move objects'.'outObjects'); 
                    }  
                    action 'Resist Front Wheels' : SystemFunction  { 
                        @CapellaID { eid = "a46e8755-90d0-49e3-90cf-7d50f840b3db"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "998e30e4-5457-4f14-bae7-aa0654f0f354"; } 
                            attribute :>> isControl = false; 
                            attribute :>> isControlType = false; 
                            attribute :>> kindOfNode = ObjectNodeKind::Unspecified; 
                            attribute :>> ordering = ObjectNodeOrderingKind::FIFO; 
                        }  
                        ref :>> inputs =  ('eRod_Autonomous_Vehicle_2024 Project'::'eRod_Autonomous_Vehicle_2024'::'System Analysis'::'System Functions'::'Root System Function'.'Resist Front Wheels'.'FIP 1'); 
                    }  
                    action 'Receive Status of Progess ' : SystemFunction  { 
                        @CapellaID { eid = "2de55593-ce2c-469c-9a9a-bd8aeaef6637"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'inParking Status' : FunctionInputPort  { 
                            @CapellaID { eid = "7fa8aaab-fb64-422e-836f-4882bf99f1d1"; } 
                            attribute :>> isControl = false; 
                            attribute :>> isControlType = false; 
                            attribute :>> kindOfNode = ObjectNodeKind::Unspecified; 
                            attribute :>> ordering = ObjectNodeOrderingKind::FIFO; 
                        }  
                         
                        ref :>> inputs =  ('eRod_Autonomous_Vehicle_2024 Project'::'eRod_Autonomous_Vehicle_2024'::'System Analysis'::'System Functions'::'Root System Function'.'Receive Status of Progess '.'inParking Status'); 
                    }  
                    interface '21737cb1-a533-4e0e-b423-e8d1c433d866' : FunctionalExchange 
                        connect source ::> 'eRod_Autonomous_Vehicle_2024 Project'::'eRod_Autonomous_Vehicle_2024'::'System Analysis'::'System Functions'::'Root System Function'.'Drive on a race track'.'outCommand'
                        to target ::> 'eRod_Autonomous_Vehicle_2024 Project'::'eRod_Autonomous_Vehicle_2024'::'System Analysis'::'System Functions'::'Root System Function'.'Sporty drive'.'inCommand' { 
                        @CapellaID { eid = "21737cb1-a533-4e0e-b423-e8d1c433d866"; } 
                        attribute :>> isMulticast = false; 
                        attribute :>> isMultireceive = false; 
                        attribute :>> kindOfRate = RateKind::Unspecified; 
                        attribute :>> interfaceName = "Command"; 
                         
                    }  
                    interface '09928616-6ea6-40cc-82a0-fb0aaa5ff578' : FunctionalExchange 
                        connect source ::> 'eRod_Autonomous_Vehicle_2024 Project'::'eRod_Autonomous_Vehicle_2024'::'System Analysis'::'System Functions'::'Root System Function'.'Stop'.'outProvide'
                        to target ::> 'eRod_Autonomous_Vehicle_2024 Project'::'eRod_Autonomous_Vehicle_2024'::'System Analysis'::'System Functions'::'Root System Function'.'Car racing experience absorbed'.'inProvide' { 
                        @CapellaID { eid = "09928616-6ea6-40cc-82a0-fb0aaa5ff578"; } 
                        attribute :>> isMulticast = false; 
                        attribute :>> isMultireceive = false; 
                        attribute :>> kindOfRate = RateKind::Unspecified; 
                        attribute :>> interfaceName = "Cause"; 
                         
                    }  
                    interface 'cdf6cd1f-fbf7-4fc5-a568-e76b603a21b9' : FunctionalExchange 
                        connect source ::> 'eRod_Autonomous_Vehicle_2024 Project'::'eRod_Autonomous_Vehicle_2024'::'System Analysis'::'System Functions'::'Root System Function'.'Motor overheating warning '.'outDisplay'
                        to target ::> 'eRod_Autonomous_Vehicle_2024 Project'::'eRod_Autonomous_Vehicle_2024'::'System Analysis'::'System Functions'::'Root System Function'.'Get informed with issues'.'inDisplay' { 
                        @CapellaID { eid = "cdf6cd1f-fbf7-4fc5-a568-e76b603a21b9"; } 
                        attribute :>> isMulticast = false; 
                        attribute :>> isMultireceive = false; 
                        attribute :>> kindOfRate = RateKind::Unspecified; 
                        attribute :>> interfaceName = "Display"; 
                         
                    }  
                    interface 'c8739b1d-878b-4b72-851e-26839aeec754' : FunctionalExchange 
                        connect source ::> 'eRod_Autonomous_Vehicle_2024 Project'::'eRod_Autonomous_Vehicle_2024'::'System Analysis'::'System Functions'::'Root System Function'.'Sporty drive'.'outCause'
                        to target ::> 'eRod_Autonomous_Vehicle_2024 Project'::'eRod_Autonomous_Vehicle_2024'::'System Analysis'::'System Functions'::'Root System Function'.'Transfer Energy'.'Acquire Energy'.'FIP 1' { 
                        @CapellaID { eid = "c8739b1d-878b-4b72-851e-26839aeec754"; } 
                        attribute :>> isMulticast = false; 
                        attribute :>> isMultireceive = false; 
                        attribute :>> kindOfRate = RateKind::Unspecified; 
                        attribute :>> interfaceName = "Signal"; 
                    }  
                    interface 'c698f103-54ac-491b-a6f4-d764baf0383c' : FunctionalExchange 
                        connect source ::> 'eRod_Autonomous_Vehicle_2024 Project'::'eRod_Autonomous_Vehicle_2024'::'System Analysis'::'System Functions'::'Root System Function'.'Get informed with issues'.'FOP 1'
                        to target ::> 'eRod_Autonomous_Vehicle_2024 Project'::'eRod_Autonomous_Vehicle_2024'::'System Analysis'::'System Functions'::'Root System Function'.'Report issues'.'FIP 1' { 
                        @CapellaID { eid = "c698f103-54ac-491b-a6f4-d764baf0383c"; } 
                        attribute :>> isMulticast = false; 
                        attribute :>> isMultireceive = false; 
                        attribute :>> kindOfRate = RateKind::Unspecified; 
                        attribute :>> interfaceName = "action"; 
                    }  
                    interface 'd3505a26-4e29-4af9-8608-c1023a575945' : FunctionalExchange 
                        connect source ::> 'eRod_Autonomous_Vehicle_2024 Project'::'eRod_Autonomous_Vehicle_2024'::'System Analysis'::'System Functions'::'Root System Function'.'Motor protect'.'Detect temperature limit'.'FOP 3'
                        to target ::> 'eRod_Autonomous_Vehicle_2024 Project'::'eRod_Autonomous_Vehicle_2024'::'System Analysis'::'System Functions'::'Root System Function'.'Motor overheating warning '.'inCause' { 
                        @CapellaID { eid = "d3505a26-4e29-4af9-8608-c1023a575945"; } 
                        attribute :>> isMulticast = false; 
                        attribute :>> isMultireceive = false; 
                        attribute :>> kindOfRate = RateKind::Unspecified; 
                        attribute :>> interfaceName = "Display signal"; 
                    }  
                    interface 'fe887ba1-b3ff-4c0e-8f2d-2e4acb6302f6' : FunctionalExchange 
                        connect source ::> 'eRod_Autonomous_Vehicle_2024 Project'::'eRod_Autonomous_Vehicle_2024'::'System Analysis'::'System Functions'::'Root System Function'.'Motor protect'.'Reduce power'.'FOP 1'
                        to target ::> 'eRod_Autonomous_Vehicle_2024 Project'::'eRod_Autonomous_Vehicle_2024'::'System Analysis'::'System Functions'::'Root System Function'.'Deaccelerate'.'FIP 1' { 
                        @CapellaID { eid = "fe887ba1-b3ff-4c0e-8f2d-2e4acb6302f6"; } 
                        attribute :>> isMulticast = false; 
                        attribute :>> isMultireceive = false; 
                        attribute :>> kindOfRate = RateKind::Unspecified; 
                        attribute :>> interfaceName = "Power"; 
                    }  
                    interface 'bbe4b2d5-09e2-426f-9c95-3c2f0942e5e2' : FunctionalExchange 
                        connect source ::> 'eRod_Autonomous_Vehicle_2024 Project'::'eRod_Autonomous_Vehicle_2024'::'System Analysis'::'System Functions'::'Root System Function'.'Deaccelerate'.'FOP 1'
                        to target ::> 'eRod_Autonomous_Vehicle_2024 Project'::'eRod_Autonomous_Vehicle_2024'::'System Analysis'::'System Functions'::'Root System Function'.'Stop'.'FIP 1' { 
                        @CapellaID { eid = "bbe4b2d5-09e2-426f-9c95-3c2f0942e5e2"; } 
                        attribute :>> isMulticast = false; 
                        attribute :>> isMultireceive = false; 
                        attribute :>> kindOfRate = RateKind::Unspecified; 
                        attribute :>> interfaceName = "Energy"; 
                    }  
                    interface '25064f56-87cc-4979-8faa-278388d7016e' : FunctionalExchange 
                        connect source ::> 'eRod_Autonomous_Vehicle_2024 Project'::'eRod_Autonomous_Vehicle_2024'::'System Analysis'::'System Functions'::'Root System Function'.'Report issues'.'FOP 1'
                        to target ::> 'eRod_Autonomous_Vehicle_2024 Project'::'eRod_Autonomous_Vehicle_2024'::'System Analysis'::'System Functions'::'Root System Function'.'Recieve feedback'.'inFeedback' { 
                        @CapellaID { eid = "25064f56-87cc-4979-8faa-278388d7016e"; } 
                        attribute :>> isMulticast = false; 
                        attribute :>> isMultireceive = false; 
                        attribute :>> kindOfRate = RateKind::Unspecified; 
                        attribute :>> interfaceName = "feedback"; 
                         
                    }  
                    interface 'f43b7ea7-8fb8-410f-adfa-0521a4349d3f' : FunctionalExchange 
                        connect source ::> 'eRod_Autonomous_Vehicle_2024 Project'::'eRod_Autonomous_Vehicle_2024'::'System Analysis'::'System Functions'::'Root System Function'.'Software update'.'Signal'
                        to target ::> 'eRod_Autonomous_Vehicle_2024 Project'::'eRod_Autonomous_Vehicle_2024'::'System Analysis'::'System Functions'::'Root System Function'.'Control temperature'.'Limit temperature'.'FIP 1' { 
                        @CapellaID { eid = "f43b7ea7-8fb8-410f-adfa-0521a4349d3f"; } 
                        attribute :>> isMulticast = false; 
                        attribute :>> isMultireceive = false; 
                        attribute :>> kindOfRate = RateKind::Unspecified; 
                        attribute :>> interfaceName = "signal"; 
                    }  
                    interface '41db3cad-802d-4343-b3aa-4b18c5dd96d5' : FunctionalExchange 
                        connect source ::> 'eRod_Autonomous_Vehicle_2024 Project'::'eRod_Autonomous_Vehicle_2024'::'System Analysis'::'System Functions'::'Root System Function'.'Transfer Energy'.'generate power'.'FOP 1'
                        to target ::> 'eRod_Autonomous_Vehicle_2024 Project'::'eRod_Autonomous_Vehicle_2024'::'System Analysis'::'System Functions'::'Root System Function'.'Control temperature'.'Limit power'.'FIP 3' { 
                        @CapellaID { eid = "41db3cad-802d-4343-b3aa-4b18c5dd96d5"; } 
                        attribute :>> isMulticast = false; 
                        attribute :>> isMultireceive = false; 
                        attribute :>> kindOfRate = RateKind::Unspecified; 
                        attribute :>> interfaceName = "Power"; 
                    }  
                    interface 'fee0d319-e733-453f-9146-6f29048c6d35' : FunctionalExchange 
                        connect source ::> 'eRod_Autonomous_Vehicle_2024 Project'::'eRod_Autonomous_Vehicle_2024'::'System Analysis'::'System Functions'::'Root System Function'.'Transfer Energy'.'Generate heat'.'FOP 1'
                        to target ::> 'eRod_Autonomous_Vehicle_2024 Project'::'eRod_Autonomous_Vehicle_2024'::'System Analysis'::'System Functions'::'Root System Function'.'Motor protect'.'Monitor temperature'.'FIP 1' { 
                        @CapellaID { eid = "fee0d319-e733-453f-9146-6f29048c6d35"; } 
                        attribute :>> isMulticast = false; 
                        attribute :>> isMultireceive = false; 
                        attribute :>> kindOfRate = RateKind::Unspecified; 
                        attribute :>> interfaceName = "Heat flow"; 
                    }  
                    interface '8b48666c-343c-4dc4-8cb1-6710f32ac69d' : FunctionalExchange 
                        connect source ::> 'eRod_Autonomous_Vehicle_2024 Project'::'eRod_Autonomous_Vehicle_2024'::'System Analysis'::'System Functions'::'Root System Function'.'Control temperature'.'Limit power'.'FOP 1'
                        to target ::> 'eRod_Autonomous_Vehicle_2024 Project'::'eRod_Autonomous_Vehicle_2024'::'System Analysis'::'System Functions'::'Root System Function'.'Sporty drive'.'FIP 3' { 
                        @CapellaID { eid = "8b48666c-343c-4dc4-8cb1-6710f32ac69d"; } 
                        attribute :>> isMulticast = false; 
                        attribute :>> isMultireceive = false; 
                        attribute :>> kindOfRate = RateKind::Unspecified; 
                        attribute :>> interfaceName = "Power"; 
                    }  
                    interface '8c5ee47e-75ad-401b-81d5-b2533b5b8b6e' : FunctionalExchange 
                        connect source ::> 'eRod_Autonomous_Vehicle_2024 Project'::'eRod_Autonomous_Vehicle_2024'::'System Analysis'::'System Functions'::'Root System Function'.'Sporty drive'.'FOP 2'
                        to target ::> 'eRod_Autonomous_Vehicle_2024 Project'::'eRod_Autonomous_Vehicle_2024'::'System Analysis'::'System Functions'::'Root System Function'.'Obtain car racing experience'.'FIP 1' { 
                        @CapellaID { eid = "8c5ee47e-75ad-401b-81d5-b2533b5b8b6e"; } 
                        attribute :>> isMulticast = false; 
                        attribute :>> isMultireceive = false; 
                        attribute :>> kindOfRate = RateKind::Unspecified; 
                        attribute :>> interfaceName = "Experience"; 
                    }  
                    interface '86fe5cc7-469e-499d-8dfe-c38fd2504e64' : FunctionalExchange 
                        connect source ::> 'eRod_Autonomous_Vehicle_2024 Project'::'eRod_Autonomous_Vehicle_2024'::'System Analysis'::'System Functions'::'Root System Function'.'Transfer Energy'.'generate power'.'FOP 1'
                        to target ::> 'eRod_Autonomous_Vehicle_2024 Project'::'eRod_Autonomous_Vehicle_2024'::'System Analysis'::'System Functions'::'Root System Function'.'Motor protect'.'Reduce power'.'FIP 1' { 
                        @CapellaID { eid = "86fe5cc7-469e-499d-8dfe-c38fd2504e64"; } 
                        attribute :>> isMulticast = false; 
                        attribute :>> isMultireceive = false; 
                        attribute :>> kindOfRate = RateKind::Unspecified; 
                        attribute :>> interfaceName = "Power"; 
                    }  
                    interface '5554cc7d-cd17-43bf-ae7b-14819bfb763e' : FunctionalExchange 
                        connect source ::> 'eRod_Autonomous_Vehicle_2024 Project'::'eRod_Autonomous_Vehicle_2024'::'System Analysis'::'System Functions'::'Root System Function'.'Software update'.'outRe-enable'
                        to target ::> 'eRod_Autonomous_Vehicle_2024 Project'::'eRod_Autonomous_Vehicle_2024'::'System Analysis'::'System Functions'::'Root System Function'.'Sporty drive'.'inRe-enable' { 
                        @CapellaID { eid = "5554cc7d-cd17-43bf-ae7b-14819bfb763e"; } 
                        attribute :>> isMulticast = false; 
                        attribute :>> isMultireceive = false; 
                        attribute :>> kindOfRate = RateKind::Unspecified; 
                        attribute :>> interfaceName = "Re-enable"; 
                         
                    }  
                    interface 'c2e16c1d-e749-4725-b483-7bb13e50d93e' : FunctionalExchange 
                        connect source ::> 'eRod_Autonomous_Vehicle_2024 Project'::'eRod_Autonomous_Vehicle_2024'::'System Analysis'::'System Functions'::'Root System Function'.'Recieve feedback'.'outSolve'
                        to target ::> 'eRod_Autonomous_Vehicle_2024 Project'::'eRod_Autonomous_Vehicle_2024'::'System Analysis'::'System Functions'::'Root System Function'.'Provide solution'.'inSolve' { 
                        @CapellaID { eid = "c2e16c1d-e749-4725-b483-7bb13e50d93e"; } 
                        attribute :>> isMulticast = false; 
                        attribute :>> isMultireceive = false; 
                        attribute :>> kindOfRate = RateKind::Unspecified; 
                        attribute :>> interfaceName = "Solve"; 
                         
                    }  
                    interface '916b2bd8-7776-4e59-92d1-9ec0f83e4c6a' : FunctionalExchange 
                        connect source ::> 'eRod_Autonomous_Vehicle_2024 Project'::'eRod_Autonomous_Vehicle_2024'::'System Analysis'::'System Functions'::'Root System Function'.'Provide solution'.'outUpdate'
                        to target ::> 'eRod_Autonomous_Vehicle_2024 Project'::'eRod_Autonomous_Vehicle_2024'::'System Analysis'::'System Functions'::'Root System Function'.'Informed Software update'.'inUpdate' { 
                        @CapellaID { eid = "916b2bd8-7776-4e59-92d1-9ec0f83e4c6a"; } 
                        attribute :>> isMulticast = false; 
                        attribute :>> isMultireceive = false; 
                        attribute :>> kindOfRate = RateKind::Unspecified; 
                        attribute :>> interfaceName = "Update"; 
                         
                    }  
                    interface '5f9dc1f8-409b-4af1-a23b-07193c0ca974' : FunctionalExchange 
                        connect source ::> 'eRod_Autonomous_Vehicle_2024 Project'::'eRod_Autonomous_Vehicle_2024'::'System Analysis'::'System Functions'::'Root System Function'.'Informed Software update'.'outApproval'
                        to target ::> 'eRod_Autonomous_Vehicle_2024 Project'::'eRod_Autonomous_Vehicle_2024'::'System Analysis'::'System Functions'::'Root System Function'.'Software update'.'inApproval' { 
                        @CapellaID { eid = "5f9dc1f8-409b-4af1-a23b-07193c0ca974"; } 
                        attribute :>> isMulticast = false; 
                        attribute :>> isMultireceive = false; 
                        attribute :>> kindOfRate = RateKind::Unspecified; 
                        attribute :>> interfaceName = "Approval"; 
                         
                    }  
                    interface 'e03fd420-1c53-4d50-b06c-f1c1a87d6e3a' : FunctionalExchange 
                        connect source ::> 'eRod_Autonomous_Vehicle_2024 Project'::'eRod_Autonomous_Vehicle_2024'::'System Analysis'::'System Functions'::'Root System Function'.'Provide solution'.'FOP 2'
                        to target ::> 'eRod_Autonomous_Vehicle_2024 Project'::'eRod_Autonomous_Vehicle_2024'::'System Analysis'::'System Functions'::'Root System Function'.'Get Software-update'.'FIP 1' { 
                        @CapellaID { eid = "e03fd420-1c53-4d50-b06c-f1c1a87d6e3a"; } 
                        attribute :>> isMulticast = false; 
                        attribute :>> isMultireceive = false; 
                        attribute :>> kindOfRate = RateKind::Unspecified; 
                        attribute :>> interfaceName = "provide"; 
                    }  
                    interface 'abab0827-19f7-442d-b63c-473eea84d95d' : FunctionalExchange 
                        connect source ::> 'eRod_Autonomous_Vehicle_2024 Project'::'eRod_Autonomous_Vehicle_2024'::'System Analysis'::'System Functions'::'Root System Function'.'Get Software-update'.'FOP 1'
                        to target ::> 'eRod_Autonomous_Vehicle_2024 Project'::'eRod_Autonomous_Vehicle_2024'::'System Analysis'::'System Functions'::'Root System Function'.'Software update'.'inApproval' { 
                        @CapellaID { eid = "abab0827-19f7-442d-b63c-473eea84d95d"; } 
                        attribute :>> isMulticast = false; 
                        attribute :>> isMultireceive = false; 
                        attribute :>> kindOfRate = RateKind::Unspecified; 
                        attribute :>> interfaceName = "Approval"; 
                    }  
                    interface '93bef316-12ff-4d4d-97f6-8f2b25851a14' : FunctionalExchange 
                        connect source ::> 'eRod_Autonomous_Vehicle_2024 Project'::'eRod_Autonomous_Vehicle_2024'::'System Analysis'::'System Functions'::'Root System Function'.'Maintain distance'.'FOP 1'
                        to target ::> 'eRod_Autonomous_Vehicle_2024 Project'::'eRod_Autonomous_Vehicle_2024'::'System Analysis'::'System Functions'::'Root System Function'.'Maintain speed'.'FIP 1' { 
                        @CapellaID { eid = "93bef316-12ff-4d4d-97f6-8f2b25851a14"; } 
                        attribute :>> isMulticast = false; 
                        attribute :>> isMultireceive = false; 
                        attribute :>> kindOfRate = RateKind::Unspecified; 
                        attribute :>> interfaceName = "Set Speed"; 
                    }  
                    interface '21c5ea50-56cf-4e17-b90e-c25092178078' : FunctionalExchange 
                        connect source ::> 'eRod_Autonomous_Vehicle_2024 Project'::'eRod_Autonomous_Vehicle_2024'::'System Analysis'::'System Functions'::'Root System Function'.'Avoid collision'.'FOP 1'
                        to target ::> 'eRod_Autonomous_Vehicle_2024 Project'::'eRod_Autonomous_Vehicle_2024'::'System Analysis'::'System Functions'::'Root System Function'.'Control braking'.'FIP 1' { 
                        @CapellaID { eid = "21c5ea50-56cf-4e17-b90e-c25092178078"; } 
                        attribute :>> isMulticast = false; 
                        attribute :>> isMultireceive = false; 
                        attribute :>> kindOfRate = RateKind::Unspecified; 
                        attribute :>> interfaceName = "Brake Command"; 
                    }  
                    interface '22434d92-754d-43b3-bd5d-87cd48be77b1' : FunctionalExchange 
                        connect source ::> 'eRod_Autonomous_Vehicle_2024 Project'::'eRod_Autonomous_Vehicle_2024'::'System Analysis'::'System Functions'::'Root System Function'.'Locate targets'.'FOP 1'
                        to target ::> 'eRod_Autonomous_Vehicle_2024 Project'::'eRod_Autonomous_Vehicle_2024'::'System Analysis'::'System Functions'::'Root System Function'.'Avoid collision'.'FIP 1' { 
                        @CapellaID { eid = "22434d92-754d-43b3-bd5d-87cd48be77b1"; } 
                        attribute :>> isMulticast = false; 
                        attribute :>> isMultireceive = false; 
                        attribute :>> kindOfRate = RateKind::Unspecified; 
                        attribute :>> interfaceName = "Locate Targets"; 
                    }  
                    interface '851fafb3-489b-4ac0-93b3-d5bead2317f5' : FunctionalExchange 
                        connect source ::> 'eRod_Autonomous_Vehicle_2024 Project'::'eRod_Autonomous_Vehicle_2024'::'System Analysis'::'System Functions'::'Root System Function'.'Provide object location'.'FOP 1'
                        to target ::> 'eRod_Autonomous_Vehicle_2024 Project'::'eRod_Autonomous_Vehicle_2024'::'System Analysis'::'System Functions'::'Root System Function'.'Locate targets'.'FIP 1' { 
                        @CapellaID { eid = "851fafb3-489b-4ac0-93b3-d5bead2317f5"; } 
                        attribute :>> isMulticast = false; 
                        attribute :>> isMultireceive = false; 
                        attribute :>> kindOfRate = RateKind::Unspecified; 
                        attribute :>> interfaceName = "Object Location"; 
                    }  
                    interface '4b235453-ef29-4b1b-9828-40efa8737c46' : FunctionalExchange 
                        connect source ::> 'eRod_Autonomous_Vehicle_2024 Project'::'eRod_Autonomous_Vehicle_2024'::'System Analysis'::'System Functions'::'Root System Function'.'Maintain distance'.'FOP 2'
                        to target ::> 'eRod_Autonomous_Vehicle_2024 Project'::'eRod_Autonomous_Vehicle_2024'::'System Analysis'::'System Functions'::'Root System Function'.'Control braking'.'FIP 2' { 
                        @CapellaID { eid = "4b235453-ef29-4b1b-9828-40efa8737c46"; } 
                        attribute :>> isMulticast = false; 
                        attribute :>> isMultireceive = false; 
                        attribute :>> kindOfRate = RateKind::Unspecified; 
                        attribute :>> interfaceName = "Active Braking"; 
                    }  
                    interface '1bea8cb7-1cf4-4dd6-8bcf-8e648e8ccea0' : FunctionalExchange 
                        connect source ::> 'eRod_Autonomous_Vehicle_2024 Project'::'eRod_Autonomous_Vehicle_2024'::'System Analysis'::'System Functions'::'Root System Function'.'Maintain distance'.'FOP 3'
                        to target ::> 'eRod_Autonomous_Vehicle_2024 Project'::'eRod_Autonomous_Vehicle_2024'::'System Analysis'::'System Functions'::'Root System Function'.'Control braking'.'FIP 3' { 
                        @CapellaID { eid = "1bea8cb7-1cf4-4dd6-8bcf-8e648e8ccea0"; } 
                        attribute :>> isMulticast = false; 
                        attribute :>> isMultireceive = false; 
                        attribute :>> kindOfRate = RateKind::Unspecified; 
                        attribute :>> interfaceName = "Brake Command"; 
                    }  
                    interface '261b8db1-fd8f-4742-a6f4-d70e8450bcee' : FunctionalExchange 
                        connect source ::> 'eRod_Autonomous_Vehicle_2024 Project'::'eRod_Autonomous_Vehicle_2024'::'System Analysis'::'System Functions'::'Root System Function'.'Control braking'.'FOP 1'
                        to target ::> 'eRod_Autonomous_Vehicle_2024 Project'::'eRod_Autonomous_Vehicle_2024'::'System Analysis'::'System Functions'::'Root System Function'.'Maintain distance'.'FIP 1' { 
                        @CapellaID { eid = "261b8db1-fd8f-4742-a6f4-d70e8450bcee"; } 
                        attribute :>> isMulticast = false; 
                        attribute :>> isMultireceive = false; 
                        attribute :>> kindOfRate = RateKind::Unspecified; 
                        attribute :>> interfaceName = "Braking"; 
                    }  
                    interface 'd115699f-c1d1-40f3-aa77-65a4aa859c71' : FunctionalExchange 
                        connect source ::> 'eRod_Autonomous_Vehicle_2024 Project'::'eRod_Autonomous_Vehicle_2024'::'System Analysis'::'System Functions'::'Root System Function'.'Provide vehicle status'.'FOP 1'
                        to target ::> 'eRod_Autonomous_Vehicle_2024 Project'::'eRod_Autonomous_Vehicle_2024'::'System Analysis'::'System Functions'::'Root System Function'.'Observe status'.'FIP 1' { 
                        @CapellaID { eid = "d115699f-c1d1-40f3-aa77-65a4aa859c71"; } 
                        attribute :>> isMulticast = false; 
                        attribute :>> isMultireceive = false; 
                        attribute :>> kindOfRate = RateKind::Unspecified; 
                        attribute :>> interfaceName = "Status"; 
                    }  
                    interface 'dc48f799-dcc2-4510-ad65-155854d64eeb' : FunctionalExchange 
                        connect source ::> 'eRod_Autonomous_Vehicle_2024 Project'::'eRod_Autonomous_Vehicle_2024'::'System Analysis'::'System Functions'::'Root System Function'.'Avoid collision'.'FOP 2'
                        to target ::> 'eRod_Autonomous_Vehicle_2024 Project'::'eRod_Autonomous_Vehicle_2024'::'System Analysis'::'System Functions'::'Root System Function'.'Provide vehicle status'.'FIP 1' { 
                        @CapellaID { eid = "dc48f799-dcc2-4510-ad65-155854d64eeb"; } 
                        attribute :>> isMulticast = false; 
                        attribute :>> isMultireceive = false; 
                        attribute :>> kindOfRate = RateKind::Unspecified; 
                        attribute :>> interfaceName = "Collsion Warning"; 
                    }  
                    interface '2d1c2035-5524-4691-ae89-77dccea3a761' : FunctionalExchange 
                        connect source ::> 'eRod_Autonomous_Vehicle_2024 Project'::'eRod_Autonomous_Vehicle_2024'::'System Analysis'::'System Functions'::'Root System Function'.'Locate targets'.'FOP 2'
                        to target ::> 'eRod_Autonomous_Vehicle_2024 Project'::'eRod_Autonomous_Vehicle_2024'::'System Analysis'::'System Functions'::'Root System Function'.'Maintain distance'.'FIP 2' { 
                        @CapellaID { eid = "2d1c2035-5524-4691-ae89-77dccea3a761"; } 
                        attribute :>> isMulticast = false; 
                        attribute :>> isMultireceive = false; 
                        attribute :>> kindOfRate = RateKind::Unspecified; 
                        attribute :>> interfaceName = "Target Locations"; 
                    }  
                    interface '4d771303-3927-4acb-811e-dfc862f247c1' : FunctionalExchange 
                        connect source ::> 'eRod_Autonomous_Vehicle_2024 Project'::'eRod_Autonomous_Vehicle_2024'::'System Analysis'::'System Functions'::'Root System Function'.'Automatic Steering'.'FOP 1'
                        to target ::> 'eRod_Autonomous_Vehicle_2024 Project'::'eRod_Autonomous_Vehicle_2024'::'System Analysis'::'System Functions'::'Root System Function'.'Steer wheels'.'FIP 1' { 
                        @CapellaID { eid = "4d771303-3927-4acb-811e-dfc862f247c1"; } 
                        attribute :>> isMulticast = false; 
                        attribute :>> isMultireceive = false; 
                        attribute :>> kindOfRate = RateKind::Unspecified; 
                        attribute :>> interfaceName = "Steer command"; 
                    }  
                    interface 'f268a0f4-a626-4206-bf93-f81df12845b7' : FunctionalExchange 
                        connect source ::> 'eRod_Autonomous_Vehicle_2024 Project'::'eRod_Autonomous_Vehicle_2024'::'System Analysis'::'System Functions'::'Root System Function'.'Avoid collision'.'FOP 3'
                        to target ::> 'eRod_Autonomous_Vehicle_2024 Project'::'eRod_Autonomous_Vehicle_2024'::'System Analysis'::'System Functions'::'Root System Function'.'Automatic Steering'.'FIP 1' { 
                        @CapellaID { eid = "f268a0f4-a626-4206-bf93-f81df12845b7"; } 
                        attribute :>> isMulticast = false; 
                        attribute :>> isMultireceive = false; 
                        attribute :>> kindOfRate = RateKind::Unspecified; 
                        attribute :>> interfaceName = "Evasive manuever"; 
                    }  
                    interface 'ed11051f-31d8-4e63-b54b-0a3ab5d8bb79' : FunctionalExchange 
                        connect source ::> 'eRod_Autonomous_Vehicle_2024 Project'::'eRod_Autonomous_Vehicle_2024'::'System Analysis'::'System Functions'::'Root System Function'.'Drive vehicle'.'FOP 1'
                        to target ::> 'eRod_Autonomous_Vehicle_2024 Project'::'eRod_Autonomous_Vehicle_2024'::'System Analysis'::'System Functions'::'Root System Function'.'Steer wheels'.'FIP 2' { 
                        @CapellaID { eid = "ed11051f-31d8-4e63-b54b-0a3ab5d8bb79"; } 
                        attribute :>> isMulticast = false; 
                        attribute :>> isMultireceive = false; 
                        attribute :>> kindOfRate = RateKind::Unspecified; 
                        attribute :>> interfaceName = "Steering angle"; 
                    }  
                    interface 'df9a5824-6a0e-4e78-8838-7952aebb53f8' : FunctionalExchange 
                        connect source ::> 'eRod_Autonomous_Vehicle_2024 Project'::'eRod_Autonomous_Vehicle_2024'::'System Analysis'::'System Functions'::'Root System Function'.'Provide road markers'.'FOP 1'
                        to target ::> 'eRod_Autonomous_Vehicle_2024 Project'::'eRod_Autonomous_Vehicle_2024'::'System Analysis'::'System Functions'::'Root System Function'.'Detect road'.'FIP 1' { 
                        @CapellaID { eid = "df9a5824-6a0e-4e78-8838-7952aebb53f8"; } 
                        attribute :>> isMulticast = false; 
                        attribute :>> isMultireceive = false; 
                        attribute :>> kindOfRate = RateKind::Unspecified; 
                        attribute :>> interfaceName = "Road markers"; 
                    }  
                    interface '08aed0f8-12c4-4b63-bde1-3d04cbffd737' : FunctionalExchange 
                        connect source ::> 'eRod_Autonomous_Vehicle_2024 Project'::'eRod_Autonomous_Vehicle_2024'::'System Analysis'::'System Functions'::'Root System Function'.'Detect road'.'FOP 1'
                        to target ::> 'eRod_Autonomous_Vehicle_2024 Project'::'eRod_Autonomous_Vehicle_2024'::'System Analysis'::'System Functions'::'Root System Function'.'Automatic Steering'.'FIP 2' { 
                        @CapellaID { eid = "08aed0f8-12c4-4b63-bde1-3d04cbffd737"; } 
                        attribute :>> isMulticast = false; 
                        attribute :>> isMultireceive = false; 
                        attribute :>> kindOfRate = RateKind::Unspecified; 
                        attribute :>> interfaceName = "Steering commands"; 
                    }  
                    interface 'cbfb0986-caef-4d30-a0d0-4180ce54e33b' : FunctionalExchange 
                        connect source ::> 'eRod_Autonomous_Vehicle_2024 Project'::'eRod_Autonomous_Vehicle_2024'::'System Analysis'::'System Functions'::'Root System Function'.'Provide target vehicle velocity'.'FOP 1'
                        to target ::> 'eRod_Autonomous_Vehicle_2024 Project'::'eRod_Autonomous_Vehicle_2024'::'System Analysis'::'System Functions'::'Root System Function'.'Locate targets'.'FIP 2' { 
                        @CapellaID { eid = "cbfb0986-caef-4d30-a0d0-4180ce54e33b"; } 
                        attribute :>> isMulticast = false; 
                        attribute :>> isMultireceive = false; 
                        attribute :>> kindOfRate = RateKind::Unspecified; 
                        attribute :>> interfaceName = "Target vehicle velocity"; 
                    }  
                    interface '05f79245-612a-49e4-a3e6-518284f38939' : FunctionalExchange 
                        connect source ::> 'eRod_Autonomous_Vehicle_2024 Project'::'eRod_Autonomous_Vehicle_2024'::'System Analysis'::'System Functions'::'Root System Function'.'Provide target vehicle velocity'.'FOP 2'
                        to target ::> 'eRod_Autonomous_Vehicle_2024 Project'::'eRod_Autonomous_Vehicle_2024'::'System Analysis'::'System Functions'::'Root System Function'.'Locate targets'.'FIP 3' { 
                        @CapellaID { eid = "05f79245-612a-49e4-a3e6-518284f38939"; } 
                        attribute :>> isMulticast = false; 
                        attribute :>> isMultireceive = false; 
                        attribute :>> kindOfRate = RateKind::Unspecified; 
                        attribute :>> interfaceName = "Target vehicle distance"; 
                    }  
                    interface '1e90612b-b18f-40bd-b1de-5ab6dc0266de' : FunctionalExchange 
                        connect source ::> 'eRod_Autonomous_Vehicle_2024 Project'::'eRod_Autonomous_Vehicle_2024'::'System Analysis'::'System Functions'::'Root System Function'.'Drive vehicle'.'FOP 2'
                        to target ::> 'eRod_Autonomous_Vehicle_2024 Project'::'eRod_Autonomous_Vehicle_2024'::'System Analysis'::'System Functions'::'Root System Function'.'Control braking'.'FIP 4' { 
                        @CapellaID { eid = "1e90612b-b18f-40bd-b1de-5ab6dc0266de"; } 
                        attribute :>> isMulticast = false; 
                        attribute :>> isMultireceive = false; 
                        attribute :>> kindOfRate = RateKind::Unspecified; 
                        attribute :>> interfaceName = "Braking"; 
                    }  
                    interface '2d2c9246-b56c-4a3c-978a-20f0fa0ec8be' : FunctionalExchange 
                        connect source ::> 'eRod_Autonomous_Vehicle_2024 Project'::'eRod_Autonomous_Vehicle_2024'::'System Analysis'::'System Functions'::'Root System Function'.'Drive vehicle'.'FOP 3'
                        to target ::> 'eRod_Autonomous_Vehicle_2024 Project'::'eRod_Autonomous_Vehicle_2024'::'System Analysis'::'System Functions'::'Root System Function'.'Maintain speed'.'FIP 2' { 
                        @CapellaID { eid = "2d2c9246-b56c-4a3c-978a-20f0fa0ec8be"; } 
                        attribute :>> isMulticast = false; 
                        attribute :>> isMultireceive = false; 
                        attribute :>> kindOfRate = RateKind::Unspecified; 
                        attribute :>> interfaceName = "Accel/Decel"; 
                    }  
                    interface 'ceaabe0e-aa52-4eab-af0f-1dbcb3e1c015' : FunctionalExchange 
                        connect source ::> 'eRod_Autonomous_Vehicle_2024 Project'::'eRod_Autonomous_Vehicle_2024'::'System Analysis'::'System Functions'::'Root System Function'.'Provide weather'.'outWeather'
                        to target ::> 'eRod_Autonomous_Vehicle_2024 Project'::'eRod_Autonomous_Vehicle_2024'::'System Analysis'::'System Functions'::'Root System Function'.'Provide diverse terrain'.'inWeather' { 
                        @CapellaID { eid = "ceaabe0e-aa52-4eab-af0f-1dbcb3e1c015"; } 
                        attribute :>> isMulticast = false; 
                        attribute :>> isMultireceive = false; 
                        attribute :>> kindOfRate = RateKind::Unspecified; 
                        attribute :>> interfaceName = "Weather"; 
                         
                    }  
                    interface 'b360b201-e1cf-480c-bd81-ca9d05a9254a' : FunctionalExchange 
                        connect source ::> 'eRod_Autonomous_Vehicle_2024 Project'::'eRod_Autonomous_Vehicle_2024'::'System Analysis'::'System Functions'::'Root System Function'.'Provide diverse terrain'.'outTerrain'
                        to target ::> 'eRod_Autonomous_Vehicle_2024 Project'::'eRod_Autonomous_Vehicle_2024'::'System Analysis'::'System Functions'::'Root System Function'.'Drive vehicle'.'inTerrain' { 
                        @CapellaID { eid = "b360b201-e1cf-480c-bd81-ca9d05a9254a"; } 
                        attribute :>> isMulticast = false; 
                        attribute :>> isMultireceive = false; 
                        attribute :>> kindOfRate = RateKind::Unspecified; 
                        attribute :>> interfaceName = "Terrain"; 
                         
                    }  
                    interface '66a113c3-0be6-494f-a159-f9751f801634' : FunctionalExchange 
                        connect source ::> 'eRod_Autonomous_Vehicle_2024 Project'::'eRod_Autonomous_Vehicle_2024'::'System Analysis'::'System Functions'::'Root System Function'.'Activate Park Assist'.'outActivate'
                        to target ::> 'eRod_Autonomous_Vehicle_2024 Project'::'eRod_Autonomous_Vehicle_2024'::'System Analysis'::'System Functions'::'Root System Function'.'Status and command indication'.'inActivate' { 
                        @CapellaID { eid = "66a113c3-0be6-494f-a159-f9751f801634"; } 
                        attribute :>> isMulticast = false; 
                        attribute :>> isMultireceive = false; 
                        attribute :>> kindOfRate = RateKind::Unspecified; 
                        attribute :>> interfaceName = "Activate"; 
                         
                    }  
                    interface 'b1c80d5d-8b10-4d51-b21d-0d3da0b1b18b' : FunctionalExchange 
                        connect source ::> 'eRod_Autonomous_Vehicle_2024 Project'::'eRod_Autonomous_Vehicle_2024'::'System Analysis'::'System Functions'::'Root System Function'.'Activate Park Assist'.'outDeactivate'
                        to target ::> 'eRod_Autonomous_Vehicle_2024 Project'::'eRod_Autonomous_Vehicle_2024'::'System Analysis'::'System Functions'::'Root System Function'.'Status and command indication'.'inDeactivate' { 
                        @CapellaID { eid = "b1c80d5d-8b10-4d51-b21d-0d3da0b1b18b"; } 
                        attribute :>> isMulticast = false; 
                        attribute :>> isMultireceive = false; 
                        attribute :>> kindOfRate = RateKind::Unspecified; 
                        attribute :>> interfaceName = "Deactivate"; 
                         
                    }  
                    interface '28d48538-7717-4d0f-86b3-26f34ccfcff0' : FunctionalExchange 
                        connect source ::> 'eRod_Autonomous_Vehicle_2024 Project'::'eRod_Autonomous_Vehicle_2024'::'System Analysis'::'System Functions'::'Root System Function'.'Drive vehicle'.'outLocation'
                        to target ::> 'eRod_Autonomous_Vehicle_2024 Project'::'eRod_Autonomous_Vehicle_2024'::'System Analysis'::'System Functions'::'Root System Function'.'Provide diverse terrain'.'inLocation' { 
                        @CapellaID { eid = "28d48538-7717-4d0f-86b3-26f34ccfcff0"; } 
                        attribute :>> isMulticast = false; 
                        attribute :>> isMultireceive = false; 
                        attribute :>> kindOfRate = RateKind::Unspecified; 
                        attribute :>> interfaceName = "Location"; 
                         
                    }  
                    interface '64ca6b82-174b-422e-a885-d86569f324b1' : FunctionalExchange 
                        connect source ::> 'eRod_Autonomous_Vehicle_2024 Project'::'eRod_Autonomous_Vehicle_2024'::'System Analysis'::'System Functions'::'Root System Function'.'Move objects'.'outObjects'
                        to target ::> 'eRod_Autonomous_Vehicle_2024 Project'::'eRod_Autonomous_Vehicle_2024'::'System Analysis'::'System Functions'::'Root System Function'.'Drive vehicle'.'inObjects' { 
                        @CapellaID { eid = "64ca6b82-174b-422e-a885-d86569f324b1"; } 
                        attribute :>> isMulticast = false; 
                        attribute :>> isMultireceive = false; 
                        attribute :>> kindOfRate = RateKind::Unspecified; 
                        attribute :>> interfaceName = "Objects"; 
                         
                    }  
                    interface 'e1303971-951c-44f8-b2c2-4482427ada98' : FunctionalExchange 
                        connect source ::> 'eRod_Autonomous_Vehicle_2024 Project'::'eRod_Autonomous_Vehicle_2024'::'System Analysis'::'System Functions'::'Root System Function'.'Steer wheels'.'FOP 1'
                        to target ::> 'eRod_Autonomous_Vehicle_2024 Project'::'eRod_Autonomous_Vehicle_2024'::'System Analysis'::'System Functions'::'Root System Function'.'Resist Front Wheels'.'FIP 1' { 
                        @CapellaID { eid = "e1303971-951c-44f8-b2c2-4482427ada98"; } 
                        attribute :>> isMulticast = false; 
                        attribute :>> isMultireceive = false; 
                        attribute :>> kindOfRate = RateKind::Unspecified; 
                        attribute :>> interfaceName = "Wheel Angles Wheel Forces"; 
                    }  
                    interface '791adf23-46b4-42ab-8846-0146cf2a19b9' : FunctionalExchange 
                        connect source ::> 'eRod_Autonomous_Vehicle_2024 Project'::'eRod_Autonomous_Vehicle_2024'::'System Analysis'::'System Functions'::'Root System Function'.'Status and command indication'.'outRequest parking'
                        to target ::> 'eRod_Autonomous_Vehicle_2024 Project'::'eRod_Autonomous_Vehicle_2024'::'System Analysis'::'System Functions'::'Root System Function'.'Park vehicle'.'inRequest parking' { 
                        @CapellaID { eid = "791adf23-46b4-42ab-8846-0146cf2a19b9"; } 
                        attribute :>> isMulticast = false; 
                        attribute :>> isMultireceive = false; 
                        attribute :>> kindOfRate = RateKind::Unspecified; 
                        attribute :>> interfaceName = "Request parking"; 
                         
                    }  
                    interface '9ef99a29-723b-4acf-a680-d3eb710a2626' : FunctionalExchange 
                        connect source ::> 'eRod_Autonomous_Vehicle_2024 Project'::'eRod_Autonomous_Vehicle_2024'::'System Analysis'::'System Functions'::'Root System Function'.'Control braking'.'outDeceleration'
                        to target ::> 'eRod_Autonomous_Vehicle_2024 Project'::'eRod_Autonomous_Vehicle_2024'::'System Analysis'::'System Functions'::'Root System Function'.'Deliver traction to surface'.'inDeceleration' { 
                        @CapellaID { eid = "9ef99a29-723b-4acf-a680-d3eb710a2626"; } 
                        attribute :>> isMulticast = false; 
                        attribute :>> isMultireceive = false; 
                        attribute :>> kindOfRate = RateKind::Unspecified; 
                        attribute :>> interfaceName = "Deceleration"; 
                         
                    }  
                    interface '7e53f548-8875-4753-827e-0c3137930f91' : FunctionalExchange 
                        connect source ::> 'eRod_Autonomous_Vehicle_2024 Project'::'eRod_Autonomous_Vehicle_2024'::'System Analysis'::'System Functions'::'Root System Function'.'Status and command indication'.'outParking Status'
                        to target ::> 'eRod_Autonomous_Vehicle_2024 Project'::'eRod_Autonomous_Vehicle_2024'::'System Analysis'::'System Functions'::'Root System Function'.'Receive Status of Progess '.'inParking Status' { 
                        @CapellaID { eid = "7e53f548-8875-4753-827e-0c3137930f91"; } 
                        attribute :>> isMulticast = false; 
                        attribute :>> isMultireceive = false; 
                        attribute :>> kindOfRate = RateKind::Unspecified; 
                        attribute :>> interfaceName = "Parking Status"; 
                         
                    }  
                    interface '4fb44178-265a-4b2c-9cc1-287f5d7ccbe7' : FunctionalExchange 
                        connect source ::> 'eRod_Autonomous_Vehicle_2024 Project'::'eRod_Autonomous_Vehicle_2024'::'System Analysis'::'System Functions'::'Root System Function'.'Maintain distance'.'outActive braking'
                        to target ::> 'eRod_Autonomous_Vehicle_2024 Project'::'eRod_Autonomous_Vehicle_2024'::'System Analysis'::'System Functions'::'Root System Function'.'Control braking'.'inActive braking' { 
                        @CapellaID { eid = "4fb44178-265a-4b2c-9cc1-287f5d7ccbe7"; } 
                        attribute :>> isMulticast = false; 
                        attribute :>> isMultireceive = false; 
                        attribute :>> kindOfRate = RateKind::Unspecified; 
                        attribute :>> interfaceName = "Active braking"; 
                         
                    }  
                    interface 'ee54ddae-801f-48a9-83d6-aa89a303ff38' : FunctionalExchange 
                        connect source ::> 'eRod_Autonomous_Vehicle_2024 Project'::'eRod_Autonomous_Vehicle_2024'::'System Analysis'::'System Functions'::'Root System Function'.'Vehicle Command'.'outVehicle Commands'
                        to target ::> 'eRod_Autonomous_Vehicle_2024 Project'::'eRod_Autonomous_Vehicle_2024'::'System Analysis'::'System Functions'::'Root System Function'.'Remote Operate Car'.'inVehicle Commands' { 
                        @CapellaID { eid = "ee54ddae-801f-48a9-83d6-aa89a303ff38"; } 
                        attribute :>> isMulticast = false; 
                        attribute :>> isMultireceive = false; 
                        attribute :>> kindOfRate = RateKind::Unspecified; 
                        attribute :>> interfaceName = "Vehicle Commands"; 
                         
                    }  
                    interface 'f54b0b7a-d8dd-4e96-8a03-c3e3f3516bfc' : FunctionalExchange 
                        connect source ::> 'eRod_Autonomous_Vehicle_2024 Project'::'eRod_Autonomous_Vehicle_2024'::'System Analysis'::'System Functions'::'Root System Function'.'Remote Operate Car'.'outInitiate Park'
                        to target ::> 'eRod_Autonomous_Vehicle_2024 Project'::'eRod_Autonomous_Vehicle_2024'::'System Analysis'::'System Functions'::'Root System Function'.'Park vehicle'.'inInitiate Park' { 
                        @CapellaID { eid = "f54b0b7a-d8dd-4e96-8a03-c3e3f3516bfc"; } 
                        attribute :>> isMulticast = false; 
                        attribute :>> isMultireceive = false; 
                        attribute :>> kindOfRate = RateKind::Unspecified; 
                        attribute :>> interfaceName = "Initiate Park"; 
                         
                    }  
                    interface '42ba7b49-d3bd-432e-b45d-12c7648470ea' : FunctionalExchange 
                        connect source ::> 'eRod_Autonomous_Vehicle_2024 Project'::'eRod_Autonomous_Vehicle_2024'::'System Analysis'::'System Functions'::'Root System Function'.'Steer Wheels Remote'.'outWheel Position'
                        to target ::> 'eRod_Autonomous_Vehicle_2024 Project'::'eRod_Autonomous_Vehicle_2024'::'System Analysis'::'System Functions'::'Root System Function'.'Deliver traction to surface'.'inWheel Position' { 
                        @CapellaID { eid = "42ba7b49-d3bd-432e-b45d-12c7648470ea"; } 
                        attribute :>> isMulticast = false; 
                        attribute :>> isMultireceive = false; 
                        attribute :>> kindOfRate = RateKind::Unspecified; 
                        attribute :>> interfaceName = "Wheel Position"; 
                         
                    }  
                    interface '1bcefe26-eb27-4aad-adb4-d8dcba87b460' : FunctionalExchange 
                        connect source ::> 'eRod_Autonomous_Vehicle_2024 Project'::'eRod_Autonomous_Vehicle_2024'::'System Analysis'::'System Functions'::'Root System Function'.'Park vehicle'.'outBraking Commands'
                        to target ::> 'eRod_Autonomous_Vehicle_2024 Project'::'eRod_Autonomous_Vehicle_2024'::'System Analysis'::'System Functions'::'Root System Function'.'Control braking'.'inBraking Commands' { 
                        @CapellaID { eid = "1bcefe26-eb27-4aad-adb4-d8dcba87b460"; } 
                        attribute :>> isMulticast = false; 
                        attribute :>> isMultireceive = false; 
                        attribute :>> kindOfRate = RateKind::Unspecified; 
                        attribute :>> interfaceName = "Braking Commands"; 
                         
                    }  
                    interface '5df12483-df3d-4b7d-98bc-7ad4c7c340a9' : FunctionalExchange 
                        connect source ::> 'eRod_Autonomous_Vehicle_2024 Project'::'eRod_Autonomous_Vehicle_2024'::'System Analysis'::'System Functions'::'Root System Function'.'Park vehicle'.'outSteering Commands'
                        to target ::> 'eRod_Autonomous_Vehicle_2024 Project'::'eRod_Autonomous_Vehicle_2024'::'System Analysis'::'System Functions'::'Root System Function'.'Steer Wheels Remote'.'inSteering Commands' { 
                        @CapellaID { eid = "5df12483-df3d-4b7d-98bc-7ad4c7c340a9"; } 
                        attribute :>> isMulticast = false; 
                        attribute :>> isMultireceive = false; 
                        attribute :>> kindOfRate = RateKind::Unspecified; 
                        attribute :>> interfaceName = "Steering Commands"; 
                         
                    }  
                    interface 'c57c6fd8-1cfb-4f41-87ea-4b32a2a8f214' : FunctionalExchange 
                        connect source ::> 'eRod_Autonomous_Vehicle_2024 Project'::'eRod_Autonomous_Vehicle_2024'::'System Analysis'::'System Functions'::'Root System Function'.'Deliver traction to surface'.'outTraction'
                        to target ::> 'eRod_Autonomous_Vehicle_2024 Project'::'eRod_Autonomous_Vehicle_2024'::'System Analysis'::'System Functions'::'Root System Function'.'Provide diverse terrain'.'inTraction' { 
                        @CapellaID { eid = "c57c6fd8-1cfb-4f41-87ea-4b32a2a8f214"; } 
                        attribute :>> isMulticast = false; 
                        attribute :>> isMultireceive = false; 
                        attribute :>> kindOfRate = RateKind::Unspecified; 
                        attribute :>> interfaceName = "Traction"; 
                         
                    }  
                     
                    ref :>> ownedFunctions =  ('eRod_Autonomous_Vehicle_2024 Project'::'eRod_Autonomous_Vehicle_2024'::'System Analysis'::'System Functions'::'Root System Function'.'Drive on a race track',
                    'eRod_Autonomous_Vehicle_2024 Project'::'eRod_Autonomous_Vehicle_2024'::'System Analysis'::'System Functions'::'Root System Function'.'Sporty drive',
                    'eRod_Autonomous_Vehicle_2024 Project'::'eRod_Autonomous_Vehicle_2024'::'System Analysis'::'System Functions'::'Root System Function'.'Car racing experience absorbed',
                    'eRod_Autonomous_Vehicle_2024 Project'::'eRod_Autonomous_Vehicle_2024'::'System Analysis'::'System Functions'::'Root System Function'.'Motor overheating warning ',
                    'eRod_Autonomous_Vehicle_2024 Project'::'eRod_Autonomous_Vehicle_2024'::'System Analysis'::'System Functions'::'Root System Function'.'Software update',
                    'eRod_Autonomous_Vehicle_2024 Project'::'eRod_Autonomous_Vehicle_2024'::'System Analysis'::'System Functions'::'Root System Function'.'Report issues',
                    'eRod_Autonomous_Vehicle_2024 Project'::'eRod_Autonomous_Vehicle_2024'::'System Analysis'::'System Functions'::'Root System Function'.'Get informed with issues',
                    'eRod_Autonomous_Vehicle_2024 Project'::'eRod_Autonomous_Vehicle_2024'::'System Analysis'::'System Functions'::'Root System Function'.'Deaccelerate',
                    'eRod_Autonomous_Vehicle_2024 Project'::'eRod_Autonomous_Vehicle_2024'::'System Analysis'::'System Functions'::'Root System Function'.'Stop',
                    'eRod_Autonomous_Vehicle_2024 Project'::'eRod_Autonomous_Vehicle_2024'::'System Analysis'::'System Functions'::'Root System Function'.'Get Software-update',
                    'eRod_Autonomous_Vehicle_2024 Project'::'eRod_Autonomous_Vehicle_2024'::'System Analysis'::'System Functions'::'Root System Function'.'Obtain car racing experience',
                    'eRod_Autonomous_Vehicle_2024 Project'::'eRod_Autonomous_Vehicle_2024'::'System Analysis'::'System Functions'::'Root System Function'.'Transfer Energy',
                    'eRod_Autonomous_Vehicle_2024 Project'::'eRod_Autonomous_Vehicle_2024'::'System Analysis'::'System Functions'::'Root System Function'.'Motor protect',
                    'eRod_Autonomous_Vehicle_2024 Project'::'eRod_Autonomous_Vehicle_2024'::'System Analysis'::'System Functions'::'Root System Function'.'Control temperature',
                    'eRod_Autonomous_Vehicle_2024 Project'::'eRod_Autonomous_Vehicle_2024'::'System Analysis'::'System Functions'::'Root System Function'.'Recieve feedback',
                    'eRod_Autonomous_Vehicle_2024 Project'::'eRod_Autonomous_Vehicle_2024'::'System Analysis'::'System Functions'::'Root System Function'.'Provide solution',
                    'eRod_Autonomous_Vehicle_2024 Project'::'eRod_Autonomous_Vehicle_2024'::'System Analysis'::'System Functions'::'Root System Function'.'Informed Software update',
                    'eRod_Autonomous_Vehicle_2024 Project'::'eRod_Autonomous_Vehicle_2024'::'System Analysis'::'System Functions'::'Root System Function'.'Status and command indication',
                    'eRod_Autonomous_Vehicle_2024 Project'::'eRod_Autonomous_Vehicle_2024'::'System Analysis'::'System Functions'::'Root System Function'.'Maintain distance',
                    'eRod_Autonomous_Vehicle_2024 Project'::'eRod_Autonomous_Vehicle_2024'::'System Analysis'::'System Functions'::'Root System Function'.'Steer Wheels Remote',
                    'eRod_Autonomous_Vehicle_2024 Project'::'eRod_Autonomous_Vehicle_2024'::'System Analysis'::'System Functions'::'Root System Function'.'Control braking',
                    'eRod_Autonomous_Vehicle_2024 Project'::'eRod_Autonomous_Vehicle_2024'::'System Analysis'::'System Functions'::'Root System Function'.'Locate targets',
                    'eRod_Autonomous_Vehicle_2024 Project'::'eRod_Autonomous_Vehicle_2024'::'System Analysis'::'System Functions'::'Root System Function'.'Maintain speed',
                    'eRod_Autonomous_Vehicle_2024 Project'::'eRod_Autonomous_Vehicle_2024'::'System Analysis'::'System Functions'::'Root System Function'.'Drive vehicle',
                    'eRod_Autonomous_Vehicle_2024 Project'::'eRod_Autonomous_Vehicle_2024'::'System Analysis'::'System Functions'::'Root System Function'.'Park vehicle',
                    'eRod_Autonomous_Vehicle_2024 Project'::'eRod_Autonomous_Vehicle_2024'::'System Analysis'::'System Functions'::'Root System Function'.'Vehicle Command',
                    'eRod_Autonomous_Vehicle_2024 Project'::'eRod_Autonomous_Vehicle_2024'::'System Analysis'::'System Functions'::'Root System Function'.'Remote Operate Car',
                    'eRod_Autonomous_Vehicle_2024 Project'::'eRod_Autonomous_Vehicle_2024'::'System Analysis'::'System Functions'::'Root System Function'.'Avoid collision',
                    'eRod_Autonomous_Vehicle_2024 Project'::'eRod_Autonomous_Vehicle_2024'::'System Analysis'::'System Functions'::'Root System Function'.'Provide object location',
                    'eRod_Autonomous_Vehicle_2024 Project'::'eRod_Autonomous_Vehicle_2024'::'System Analysis'::'System Functions'::'Root System Function'.'Observe status',
                    'eRod_Autonomous_Vehicle_2024 Project'::'eRod_Autonomous_Vehicle_2024'::'System Analysis'::'System Functions'::'Root System Function'.'Provide vehicle status',
                    'eRod_Autonomous_Vehicle_2024 Project'::'eRod_Autonomous_Vehicle_2024'::'System Analysis'::'System Functions'::'Root System Function'.'Steer wheels',
                    'eRod_Autonomous_Vehicle_2024 Project'::'eRod_Autonomous_Vehicle_2024'::'System Analysis'::'System Functions'::'Root System Function'.'Automatic Steering',
                    'eRod_Autonomous_Vehicle_2024 Project'::'eRod_Autonomous_Vehicle_2024'::'System Analysis'::'System Functions'::'Root System Function'.'Detect road',
                    'eRod_Autonomous_Vehicle_2024 Project'::'eRod_Autonomous_Vehicle_2024'::'System Analysis'::'System Functions'::'Root System Function'.'Provide road markers',
                    'eRod_Autonomous_Vehicle_2024 Project'::'eRod_Autonomous_Vehicle_2024'::'System Analysis'::'System Functions'::'Root System Function'.'Provide target vehicle velocity',
                    'eRod_Autonomous_Vehicle_2024 Project'::'eRod_Autonomous_Vehicle_2024'::'System Analysis'::'System Functions'::'Root System Function'.'Provide diverse terrain',
                    'eRod_Autonomous_Vehicle_2024 Project'::'eRod_Autonomous_Vehicle_2024'::'System Analysis'::'System Functions'::'Root System Function'.'Provide parking location',
                    'eRod_Autonomous_Vehicle_2024 Project'::'eRod_Autonomous_Vehicle_2024'::'System Analysis'::'System Functions'::'Root System Function'.'Activate Park Assist',
                    'eRod_Autonomous_Vehicle_2024 Project'::'eRod_Autonomous_Vehicle_2024'::'System Analysis'::'System Functions'::'Root System Function'.'Deliver traction to surface',
                    'eRod_Autonomous_Vehicle_2024 Project'::'eRod_Autonomous_Vehicle_2024'::'System Analysis'::'System Functions'::'Root System Function'.'Provide weather',
                    'eRod_Autonomous_Vehicle_2024 Project'::'eRod_Autonomous_Vehicle_2024'::'System Analysis'::'System Functions'::'Root System Function'.'Move objects',
                    'eRod_Autonomous_Vehicle_2024 Project'::'eRod_Autonomous_Vehicle_2024'::'System Analysis'::'System Functions'::'Root System Function'.'Resist Front Wheels',
                    'eRod_Autonomous_Vehicle_2024 Project'::'eRod_Autonomous_Vehicle_2024'::'System Analysis'::'System Functions'::'Root System Function'.'Receive Status of Progess '); 
                    ref :>> ownedFunctionalExchanges =  ('eRod_Autonomous_Vehicle_2024 Project'::'eRod_Autonomous_Vehicle_2024'::'System Analysis'::'System Functions'::'Root System Function'.'21737cb1-a533-4e0e-b423-e8d1c433d866',
                    'eRod_Autonomous_Vehicle_2024 Project'::'eRod_Autonomous_Vehicle_2024'::'System Analysis'::'System Functions'::'Root System Function'.'09928616-6ea6-40cc-82a0-fb0aaa5ff578',
                    'eRod_Autonomous_Vehicle_2024 Project'::'eRod_Autonomous_Vehicle_2024'::'System Analysis'::'System Functions'::'Root System Function'.'cdf6cd1f-fbf7-4fc5-a568-e76b603a21b9',
                    'eRod_Autonomous_Vehicle_2024 Project'::'eRod_Autonomous_Vehicle_2024'::'System Analysis'::'System Functions'::'Root System Function'.'c8739b1d-878b-4b72-851e-26839aeec754',
                    'eRod_Autonomous_Vehicle_2024 Project'::'eRod_Autonomous_Vehicle_2024'::'System Analysis'::'System Functions'::'Root System Function'.'c698f103-54ac-491b-a6f4-d764baf0383c',
                    'eRod_Autonomous_Vehicle_2024 Project'::'eRod_Autonomous_Vehicle_2024'::'System Analysis'::'System Functions'::'Root System Function'.'d3505a26-4e29-4af9-8608-c1023a575945',
                    'eRod_Autonomous_Vehicle_2024 Project'::'eRod_Autonomous_Vehicle_2024'::'System Analysis'::'System Functions'::'Root System Function'.'fe887ba1-b3ff-4c0e-8f2d-2e4acb6302f6',
                    'eRod_Autonomous_Vehicle_2024 Project'::'eRod_Autonomous_Vehicle_2024'::'System Analysis'::'System Functions'::'Root System Function'.'bbe4b2d5-09e2-426f-9c95-3c2f0942e5e2',
                    'eRod_Autonomous_Vehicle_2024 Project'::'eRod_Autonomous_Vehicle_2024'::'System Analysis'::'System Functions'::'Root System Function'.'25064f56-87cc-4979-8faa-278388d7016e',
                    'eRod_Autonomous_Vehicle_2024 Project'::'eRod_Autonomous_Vehicle_2024'::'System Analysis'::'System Functions'::'Root System Function'.'f43b7ea7-8fb8-410f-adfa-0521a4349d3f',
                    'eRod_Autonomous_Vehicle_2024 Project'::'eRod_Autonomous_Vehicle_2024'::'System Analysis'::'System Functions'::'Root System Function'.'41db3cad-802d-4343-b3aa-4b18c5dd96d5',
                    'eRod_Autonomous_Vehicle_2024 Project'::'eRod_Autonomous_Vehicle_2024'::'System Analysis'::'System Functions'::'Root System Function'.'fee0d319-e733-453f-9146-6f29048c6d35',
                    'eRod_Autonomous_Vehicle_2024 Project'::'eRod_Autonomous_Vehicle_2024'::'System Analysis'::'System Functions'::'Root System Function'.'8b48666c-343c-4dc4-8cb1-6710f32ac69d',
                    'eRod_Autonomous_Vehicle_2024 Project'::'eRod_Autonomous_Vehicle_2024'::'System Analysis'::'System Functions'::'Root System Function'.'8c5ee47e-75ad-401b-81d5-b2533b5b8b6e',
                    'eRod_Autonomous_Vehicle_2024 Project'::'eRod_Autonomous_Vehicle_2024'::'System Analysis'::'System Functions'::'Root System Function'.'86fe5cc7-469e-499d-8dfe-c38fd2504e64',
                    'eRod_Autonomous_Vehicle_2024 Project'::'eRod_Autonomous_Vehicle_2024'::'System Analysis'::'System Functions'::'Root System Function'.'5554cc7d-cd17-43bf-ae7b-14819bfb763e',
                    'eRod_Autonomous_Vehicle_2024 Project'::'eRod_Autonomous_Vehicle_2024'::'System Analysis'::'System Functions'::'Root System Function'.'c2e16c1d-e749-4725-b483-7bb13e50d93e',
                    'eRod_Autonomous_Vehicle_2024 Project'::'eRod_Autonomous_Vehicle_2024'::'System Analysis'::'System Functions'::'Root System Function'.'916b2bd8-7776-4e59-92d1-9ec0f83e4c6a',
                    'eRod_Autonomous_Vehicle_2024 Project'::'eRod_Autonomous_Vehicle_2024'::'System Analysis'::'System Functions'::'Root System Function'.'5f9dc1f8-409b-4af1-a23b-07193c0ca974',
                    'eRod_Autonomous_Vehicle_2024 Project'::'eRod_Autonomous_Vehicle_2024'::'System Analysis'::'System Functions'::'Root System Function'.'e03fd420-1c53-4d50-b06c-f1c1a87d6e3a',
                    'eRod_Autonomous_Vehicle_2024 Project'::'eRod_Autonomous_Vehicle_2024'::'System Analysis'::'System Functions'::'Root System Function'.'abab0827-19f7-442d-b63c-473eea84d95d',
                    'eRod_Autonomous_Vehicle_2024 Project'::'eRod_Autonomous_Vehicle_2024'::'System Analysis'::'System Functions'::'Root System Function'.'93bef316-12ff-4d4d-97f6-8f2b25851a14',
                    'eRod_Autonomous_Vehicle_2024 Project'::'eRod_Autonomous_Vehicle_2024'::'System Analysis'::'System Functions'::'Root System Function'.'21c5ea50-56cf-4e17-b90e-c25092178078',
                    'eRod_Autonomous_Vehicle_2024 Project'::'eRod_Autonomous_Vehicle_2024'::'System Analysis'::'System Functions'::'Root System Function'.'22434d92-754d-43b3-bd5d-87cd48be77b1',
                    'eRod_Autonomous_Vehicle_2024 Project'::'eRod_Autonomous_Vehicle_2024'::'System Analysis'::'System Functions'::'Root System Function'.'851fafb3-489b-4ac0-93b3-d5bead2317f5',
                    'eRod_Autonomous_Vehicle_2024 Project'::'eRod_Autonomous_Vehicle_2024'::'System Analysis'::'System Functions'::'Root System Function'.'4b235453-ef29-4b1b-9828-40efa8737c46',
                    'eRod_Autonomous_Vehicle_2024 Project'::'eRod_Autonomous_Vehicle_2024'::'System Analysis'::'System Functions'::'Root System Function'.'1bea8cb7-1cf4-4dd6-8bcf-8e648e8ccea0',
                    'eRod_Autonomous_Vehicle_2024 Project'::'eRod_Autonomous_Vehicle_2024'::'System Analysis'::'System Functions'::'Root System Function'.'261b8db1-fd8f-4742-a6f4-d70e8450bcee',
                    'eRod_Autonomous_Vehicle_2024 Project'::'eRod_Autonomous_Vehicle_2024'::'System Analysis'::'System Functions'::'Root System Function'.'d115699f-c1d1-40f3-aa77-65a4aa859c71',
                    'eRod_Autonomous_Vehicle_2024 Project'::'eRod_Autonomous_Vehicle_2024'::'System Analysis'::'System Functions'::'Root System Function'.'dc48f799-dcc2-4510-ad65-155854d64eeb',
                    'eRod_Autonomous_Vehicle_2024 Project'::'eRod_Autonomous_Vehicle_2024'::'System Analysis'::'System Functions'::'Root System Function'.'2d1c2035-5524-4691-ae89-77dccea3a761',
                    'eRod_Autonomous_Vehicle_2024 Project'::'eRod_Autonomous_Vehicle_2024'::'System Analysis'::'System Functions'::'Root System Function'.'4d771303-3927-4acb-811e-dfc862f247c1',
                    'eRod_Autonomous_Vehicle_2024 Project'::'eRod_Autonomous_Vehicle_2024'::'System Analysis'::'System Functions'::'Root System Function'.'f268a0f4-a626-4206-bf93-f81df12845b7',
                    'eRod_Autonomous_Vehicle_2024 Project'::'eRod_Autonomous_Vehicle_2024'::'System Analysis'::'System Functions'::'Root System Function'.'ed11051f-31d8-4e63-b54b-0a3ab5d8bb79',
                    'eRod_Autonomous_Vehicle_2024 Project'::'eRod_Autonomous_Vehicle_2024'::'System Analysis'::'System Functions'::'Root System Function'.'df9a5824-6a0e-4e78-8838-7952aebb53f8',
                    'eRod_Autonomous_Vehicle_2024 Project'::'eRod_Autonomous_Vehicle_2024'::'System Analysis'::'System Functions'::'Root System Function'.'08aed0f8-12c4-4b63-bde1-3d04cbffd737',
                    'eRod_Autonomous_Vehicle_2024 Project'::'eRod_Autonomous_Vehicle_2024'::'System Analysis'::'System Functions'::'Root System Function'.'cbfb0986-caef-4d30-a0d0-4180ce54e33b',
                    'eRod_Autonomous_Vehicle_2024 Project'::'eRod_Autonomous_Vehicle_2024'::'System Analysis'::'System Functions'::'Root System Function'.'05f79245-612a-49e4-a3e6-518284f38939',
                    'eRod_Autonomous_Vehicle_2024 Project'::'eRod_Autonomous_Vehicle_2024'::'System Analysis'::'System Functions'::'Root System Function'.'1e90612b-b18f-40bd-b1de-5ab6dc0266de',
                    'eRod_Autonomous_Vehicle_2024 Project'::'eRod_Autonomous_Vehicle_2024'::'System Analysis'::'System Functions'::'Root System Function'.'2d2c9246-b56c-4a3c-978a-20f0fa0ec8be',
                    'eRod_Autonomous_Vehicle_2024 Project'::'eRod_Autonomous_Vehicle_2024'::'System Analysis'::'System Functions'::'Root System Function'.'ceaabe0e-aa52-4eab-af0f-1dbcb3e1c015',
                    'eRod_Autonomous_Vehicle_2024 Project'::'eRod_Autonomous_Vehicle_2024'::'System Analysis'::'System Functions'::'Root System Function'.'b360b201-e1cf-480c-bd81-ca9d05a9254a',
                    'eRod_Autonomous_Vehicle_2024 Project'::'eRod_Autonomous_Vehicle_2024'::'System Analysis'::'System Functions'::'Root System Function'.'66a113c3-0be6-494f-a159-f9751f801634',
                    'eRod_Autonomous_Vehicle_2024 Project'::'eRod_Autonomous_Vehicle_2024'::'System Analysis'::'System Functions'::'Root System Function'.'b1c80d5d-8b10-4d51-b21d-0d3da0b1b18b',
                    'eRod_Autonomous_Vehicle_2024 Project'::'eRod_Autonomous_Vehicle_2024'::'System Analysis'::'System Functions'::'Root System Function'.'28d48538-7717-4d0f-86b3-26f34ccfcff0',
                    'eRod_Autonomous_Vehicle_2024 Project'::'eRod_Autonomous_Vehicle_2024'::'System Analysis'::'System Functions'::'Root System Function'.'64ca6b82-174b-422e-a885-d86569f324b1',
                    'eRod_Autonomous_Vehicle_2024 Project'::'eRod_Autonomous_Vehicle_2024'::'System Analysis'::'System Functions'::'Root System Function'.'e1303971-951c-44f8-b2c2-4482427ada98',
                    'eRod_Autonomous_Vehicle_2024 Project'::'eRod_Autonomous_Vehicle_2024'::'System Analysis'::'System Functions'::'Root System Function'.'791adf23-46b4-42ab-8846-0146cf2a19b9',
                    'eRod_Autonomous_Vehicle_2024 Project'::'eRod_Autonomous_Vehicle_2024'::'System Analysis'::'System Functions'::'Root System Function'.'9ef99a29-723b-4acf-a680-d3eb710a2626',
                    'eRod_Autonomous_Vehicle_2024 Project'::'eRod_Autonomous_Vehicle_2024'::'System Analysis'::'System Functions'::'Root System Function'.'7e53f548-8875-4753-827e-0c3137930f91',
                    'eRod_Autonomous_Vehicle_2024 Project'::'eRod_Autonomous_Vehicle_2024'::'System Analysis'::'System Functions'::'Root System Function'.'4fb44178-265a-4b2c-9cc1-287f5d7ccbe7',
                    'eRod_Autonomous_Vehicle_2024 Project'::'eRod_Autonomous_Vehicle_2024'::'System Analysis'::'System Functions'::'Root System Function'.'ee54ddae-801f-48a9-83d6-aa89a303ff38',
                    'eRod_Autonomous_Vehicle_2024 Project'::'eRod_Autonomous_Vehicle_2024'::'System Analysis'::'System Functions'::'Root System Function'.'f54b0b7a-d8dd-4e96-8a03-c3e3f3516bfc',
                    'eRod_Autonomous_Vehicle_2024 Project'::'eRod_Autonomous_Vehicle_2024'::'System Analysis'::'System Functions'::'Root System Function'.'42ba7b49-d3bd-432e-b45d-12c7648470ea',
                    'eRod_Autonomous_Vehicle_2024 Project'::'eRod_Autonomous_Vehicle_2024'::'System Analysis'::'System Functions'::'Root System Function'.'1bcefe26-eb27-4aad-adb4-d8dcba87b460',
                    'eRod_Autonomous_Vehicle_2024 Project'::'eRod_Autonomous_Vehicle_2024'::'System Analysis'::'System Functions'::'Root System Function'.'5df12483-df3d-4b7d-98bc-7ad4c7c340a9',
                    'eRod_Autonomous_Vehicle_2024 Project'::'eRod_Autonomous_Vehicle_2024'::'System Analysis'::'System Functions'::'Root System Function'.'c57c6fd8-1cfb-4f41-87ea-4b32a2a8f214'); 
                     
                }  
            } 
            package  'Interfaces' {
                @PackageMeta {
                    type = "InterfacePkg";
                } 
                @CapellaID { eid = "a288a7a6-32c7-4d60-ade6-6ed171367bc7"; } 
            } 
            package  'Data' {
                @PackageMeta {
                    type = "DataPkg";
                } 
                @CapellaID { eid = "67b866e0-2e7a-4793-925f-a180b15b0cee"; } 
                package  'Predefined Types' {
                    @PackageMeta {
                        type = "DataPkg";
                    } 
                    @CapellaID { eid = "06b2ac64-f316-4153-af1b-e8765725a093"; } 
                } 
            } 
            package  'Capabilities' {
                @PackageMeta {
                    type = "CapabilityPkg";
                } 
                @CapellaID { eid = "0d1b743e-60ee-41c7-a128-3ee5c61643ae"; } 
                use case 'Software Update' : Capability { 
                    @CapellaID { eid = "99539225-271a-48c1-80f9-676c745e8fa3"; } 
                    attribute :>> summary = "Provide the capability of remote update to solve some problem in short-term or optimize the performance"; 
                    ref action '4c004c9a-428b-49ff-bf12-ce3cb9ac1690' = 'eRod_Autonomous_Vehicle_2024 Project'::'eRod_Autonomous_Vehicle_2024'::'System Analysis'::'System Functions'::'Root System Function'.'Control temperature'.'Limit power'; 
                    ref action '78742557-d908-49f2-8017-4796378dc3c7' = 'eRod_Autonomous_Vehicle_2024 Project'::'eRod_Autonomous_Vehicle_2024'::'System Analysis'::'System Functions'::'Root System Function'.'Control temperature'.'Limit temperature'; 
                    ref action '7a911895-d179-43f4-9928-82536b513df6' = 'eRod_Autonomous_Vehicle_2024 Project'::'eRod_Autonomous_Vehicle_2024'::'System Analysis'::'System Functions'::'Root System Function'.'Software update'; 
                    actor 'eRod' = 'eRod_Autonomous_Vehicle_2024 Project'::'eRod_Autonomous_Vehicle_2024'::'System Analysis'::'Structure'::'eRod'; 
                    actor 'Driver' = 'eRod_Autonomous_Vehicle_2024 Project'::'eRod_Autonomous_Vehicle_2024'::'System Analysis'::'Structure'::'Driver'; 
                    actor 'eRod Manufactor' = 'eRod_Autonomous_Vehicle_2024 Project'::'eRod_Autonomous_Vehicle_2024'::'System Analysis'::'Structure'::'eRod Manufactor'; 
                     
                     
                }  
                use case 'Sporty drive' : Capability { 
                    @CapellaID { eid = "c04b5585-f32f-465a-add7-4c38022141f7"; } 
                    ref action '64a625ae-50ea-4b61-96c2-a934a1994ca5' = 'eRod_Autonomous_Vehicle_2024 Project'::'eRod_Autonomous_Vehicle_2024'::'System Analysis'::'System Functions'::'Root System Function'.'Sporty drive'; 
                    ref action '19ed04c1-eb61-4d32-b400-74ea1369069c' = 'eRod_Autonomous_Vehicle_2024 Project'::'eRod_Autonomous_Vehicle_2024'::'System Analysis'::'System Functions'::'Root System Function'.'Transfer Energy'; 
                    ref action 'fd417c55-3c72-4d70-ad9f-a8fb46209025' = 'eRod_Autonomous_Vehicle_2024 Project'::'eRod_Autonomous_Vehicle_2024'::'System Analysis'::'System Functions'::'Root System Function'.'Vehicle Steering'; 
                    actor 'eRod' = 'eRod_Autonomous_Vehicle_2024 Project'::'eRod_Autonomous_Vehicle_2024'::'System Analysis'::'Structure'::'eRod'; 
                    actor 'Driver' = 'eRod_Autonomous_Vehicle_2024 Project'::'eRod_Autonomous_Vehicle_2024'::'System Analysis'::'Structure'::'Driver'; 
                     
                     
                }  
                use case 'Improve performance' : Capability { 
                    @CapellaID { eid = "b26720b3-05c0-4305-a47e-9479c0014d5a"; } 
                    actor 'eRod' = 'eRod_Autonomous_Vehicle_2024 Project'::'eRod_Autonomous_Vehicle_2024'::'System Analysis'::'Structure'::'eRod'; 
                     
                }  
                use case 'Finish race track' : Capability { 
                    @CapellaID { eid = "e50c8b2a-d64e-480d-bdc2-c31e93f6c385"; } 
                    actor 'eRod' = 'eRod_Autonomous_Vehicle_2024 Project'::'eRod_Autonomous_Vehicle_2024'::'System Analysis'::'Structure'::'eRod'; 
                     
                }  
                use case 'Quick solution for the issues' : Capability { 
                    @CapellaID { eid = "751bebf1-0bc7-4774-90f3-14882fb72318"; } 
                    include 'eRod_Autonomous_Vehicle_2024 Project'::'eRod_Autonomous_Vehicle_2024'::'System Analysis'::'Capabilities'::'Software Update'; 
                    actor 'eRod' = 'eRod_Autonomous_Vehicle_2024 Project'::'eRod_Autonomous_Vehicle_2024'::'System Analysis'::'Structure'::'eRod'; 
                     
                }  
                use case 'Maintain Distance to Lead Car' : Capability { 
                    @CapellaID { eid = "06bacaeb-f721-4f3f-8173-a1aaac556876"; } 
                    include 'eRod_Autonomous_Vehicle_2024 Project'::'eRod_Autonomous_Vehicle_2024'::'System Analysis'::'Capabilities'::'Adaptive Cruise Control (ACC)'; 
                    ref action 'd273384e-1e3c-4ad7-992c-d4bff401e0c2' = 'eRod_Autonomous_Vehicle_2024 Project'::'eRod_Autonomous_Vehicle_2024'::'System Analysis'::'System Functions'::'Root System Function'.'Maintain distance'; 
                    actor 'eRod' = 'eRod_Autonomous_Vehicle_2024 Project'::'eRod_Autonomous_Vehicle_2024'::'System Analysis'::'Structure'::'eRod'; 
                     
                }  
                use case 'Park Assist' : Capability { 
                    @CapellaID { eid = "4793d5b7-2258-4553-98b1-aa86ac1a1923"; } 
                    actor 'eRod' = 'eRod_Autonomous_Vehicle_2024 Project'::'eRod_Autonomous_Vehicle_2024'::'System Analysis'::'Structure'::'eRod'; 
                     
                }  
                use case 'Forward Collision Warning (FCW)' : Capability { 
                    @CapellaID { eid = "6be2d539-3f86-40f1-8aff-96891dd8e041"; } 
                    ref action '4e8315c8-cc46-4d9a-86fe-55e39b9fd7f3' = 'eRod_Autonomous_Vehicle_2024 Project'::'eRod_Autonomous_Vehicle_2024'::'System Analysis'::'System Functions'::'Root System Function'.'Forward Collision Warning (FCW)'; 
                    actor 'eRod' = 'eRod_Autonomous_Vehicle_2024 Project'::'eRod_Autonomous_Vehicle_2024'::'System Analysis'::'Structure'::'eRod'; 
                }  
                use case 'Adaptive Cruise Control (ACC)' : Capability { 
                    @CapellaID { eid = "6ed7c884-f072-434c-bbd3-12b311248df6"; } 
                    ref action '251b81ec-25c3-409f-9c06-05641df01073' = 'eRod_Autonomous_Vehicle_2024 Project'::'eRod_Autonomous_Vehicle_2024'::'System Analysis'::'System Functions'::'Root System Function'.'Adaptive Cruise Control (ACC)'; 
                    actor 'eRod' = 'eRod_Autonomous_Vehicle_2024 Project'::'eRod_Autonomous_Vehicle_2024'::'System Analysis'::'Structure'::'eRod'; 
                }  
                use case 'Autonomous Emergency Braking (AEB)' : Capability { 
                    @CapellaID { eid = "f1c23559-4e78-4c4e-888f-059ad6ae3039"; } 
                    ref action 'af98c498-80a0-4c54-b8a2-064084ce905a' = 'eRod_Autonomous_Vehicle_2024 Project'::'eRod_Autonomous_Vehicle_2024'::'System Analysis'::'System Functions'::'Root System Function'.'Adaptive Cruise Control (ACC)'; 
                    actor 'eRod' = 'eRod_Autonomous_Vehicle_2024 Project'::'eRod_Autonomous_Vehicle_2024'::'System Analysis'::'Structure'::'eRod'; 
                }  
                use case 'Avoid Collision' : Capability { 
                    @CapellaID { eid = "237dbf6a-0a4f-4e81-9f22-edb4984b2b1e"; } 
                    include 'eRod_Autonomous_Vehicle_2024 Project'::'eRod_Autonomous_Vehicle_2024'::'System Analysis'::'Capabilities'::'Adaptive Cruise Control (ACC)'; 
                    include 'eRod_Autonomous_Vehicle_2024 Project'::'eRod_Autonomous_Vehicle_2024'::'System Analysis'::'Capabilities'::'Autonomous Emergency Braking (AEB)'; 
                    include 'eRod_Autonomous_Vehicle_2024 Project'::'eRod_Autonomous_Vehicle_2024'::'System Analysis'::'Capabilities'::'Forward Collision Warning (FCW)'; 
                    include 'eRod_Autonomous_Vehicle_2024 Project'::'eRod_Autonomous_Vehicle_2024'::'System Analysis'::'Capabilities'::'Lane Keeping Assistant (LKA)'; 
                    include 'eRod_Autonomous_Vehicle_2024 Project'::'eRod_Autonomous_Vehicle_2024'::'System Analysis'::'Capabilities'::'Cross Traffic Warning (CTW)'; 
                    ref action 'd875378f-18d9-447d-809e-52e6b8214d33' = 'eRod_Autonomous_Vehicle_2024 Project'::'eRod_Autonomous_Vehicle_2024'::'System Analysis'::'System Functions'::'Root System Function'.'Avoid collision'; 
                    actor 'eRod' = 'eRod_Autonomous_Vehicle_2024 Project'::'eRod_Autonomous_Vehicle_2024'::'System Analysis'::'Structure'::'eRod'; 
                    actor 'Driver' = 'eRod_Autonomous_Vehicle_2024 Project'::'eRod_Autonomous_Vehicle_2024'::'System Analysis'::'Structure'::'Driver'; 
                     
                }  
                use case 'Lane Keeping Assistant (LKA)' : Capability { 
                    @CapellaID { eid = "877c9f8e-91f6-44ca-a063-f329a96ffeee"; } 
                    ref action '0bfe4c86-98cd-4259-bb56-1104cea2cff8' = 'eRod_Autonomous_Vehicle_2024 Project'::'eRod_Autonomous_Vehicle_2024'::'System Analysis'::'System Functions'::'Root System Function'.'Lane Keep Assist (LKA)'; 
                    actor 'eRod' = 'eRod_Autonomous_Vehicle_2024 Project'::'eRod_Autonomous_Vehicle_2024'::'System Analysis'::'Structure'::'eRod'; 
                }  
                use case 'Cross Traffic Warning (CTW)' : Capability { 
                    @CapellaID { eid = "02ae973a-d909-4dd4-a010-c6b1c892e357"; } 
                    actor 'eRod' = 'eRod_Autonomous_Vehicle_2024 Project'::'eRod_Autonomous_Vehicle_2024'::'System Analysis'::'Structure'::'eRod'; 
                }  
                use case 'Traffic Sign Recognition' : Capability { 
                    @CapellaID { eid = "f3436451-b5f9-440c-b560-79dbb68dc44f"; } 
                    include 'eRod_Autonomous_Vehicle_2024 Project'::'eRod_Autonomous_Vehicle_2024'::'System Analysis'::'Capabilities'::'Adaptive Cruise Control (ACC)'; 
                    actor 'eRod' = 'eRod_Autonomous_Vehicle_2024 Project'::'eRod_Autonomous_Vehicle_2024'::'System Analysis'::'Structure'::'eRod'; 
                     
                }  
                use case 'Driving Assistance' : Capability { 
                    @CapellaID { eid = "1a625af0-4883-4c08-b033-7f70765abb3c"; } 
                    include 'eRod_Autonomous_Vehicle_2024 Project'::'eRod_Autonomous_Vehicle_2024'::'System Analysis'::'Capabilities'::'Traffic Sign Recognition'; 
                    include 'eRod_Autonomous_Vehicle_2024 Project'::'eRod_Autonomous_Vehicle_2024'::'System Analysis'::'Capabilities'::'Park Assist'; 
                    actor 'eRod' = 'eRod_Autonomous_Vehicle_2024 Project'::'eRod_Autonomous_Vehicle_2024'::'System Analysis'::'Structure'::'eRod'; 
                     
                }  
                use case 'Autonmous Driving' : Capability { 
                    @CapellaID { eid = "44d7a0c1-544d-4ae1-92c4-bdf02ebaa23d"; } 
                    ref action 'be294a0c-0846-4779-8797-6bbcae29a2e0' = 'eRod_Autonomous_Vehicle_2024 Project'::'eRod_Autonomous_Vehicle_2024'::'System Analysis'::'System Functions'::'Root System Function'.'Lane Keep Assist (LKA)'; 
                    actor 'Driver' = 'eRod_Autonomous_Vehicle_2024 Project'::'eRod_Autonomous_Vehicle_2024'::'System Analysis'::'Structure'::'Driver'; 
                     
                     
                }  
                use case 'Remote Park' : Capability { 
                    @CapellaID { eid = "aad9f4a5-526b-49fe-80d5-2253da13122e"; } 
                    actor 'Remote Driver' = 'eRod_Autonomous_Vehicle_2024 Project'::'eRod_Autonomous_Vehicle_2024'::'System Analysis'::'Structure'::'Remote Driver'; 
                     
                     
                }  
                use case 'Bluetooth Pair Request' : Capability { 
                    @CapellaID { eid = "4cb0ba62-9dbd-48fd-b767-972b9d6f4fee"; } 
                    actor 'eRod' = 'eRod_Autonomous_Vehicle_2024 Project'::'eRod_Autonomous_Vehicle_2024'::'System Analysis'::'Structure'::'eRod'; 
                }  
            } 
            package  'Missions' {
                @PackageMeta {
                    type = "MissionPkg";
                } 
                @CapellaID { eid = "94aa913e-523e-4aab-9119-cbb5c13846a3"; } 
                use case 'Always connected' : Mission  { 
                    @CapellaID { eid = "f1d3fde8-4c1c-4fee-abd9-cea31ce6675c"; } 
                    attribute :>> summary = "The performance data is connected in cloud and can be accessed remotely"; 
                    actor 'Driver' = 'eRod_Autonomous_Vehicle_2024 Project'::'eRod_Autonomous_Vehicle_2024'::'System Analysis'::'Structure'::'Driver'; 
                }  
                use case 'Personalized driving experience' : Mission  { 
                    @CapellaID { eid = "804ee009-201f-4506-9344-67f15a80f02e"; } 
                }  
                use case 'Predictive maintenance' : Mission  { 
                    @CapellaID { eid = "ae067385-8a10-4f51-ab5d-921eb0c85e17"; } 
                }  
                use case 'Remote Update' : Mission  { 
                    @CapellaID { eid = "d0f846bb-2692-4382-8783-942fdc74ad23"; } 
                    actor 'Driver' = 'eRod_Autonomous_Vehicle_2024 Project'::'eRod_Autonomous_Vehicle_2024'::'System Analysis'::'Structure'::'Driver'; 
                    include 'eRod_Autonomous_Vehicle_2024 Project'::'eRod_Autonomous_Vehicle_2024'::'System Analysis'::'Capabilities'::'Software Update'; 
                    include 'eRod_Autonomous_Vehicle_2024 Project'::'eRod_Autonomous_Vehicle_2024'::'System Analysis'::'Capabilities'::'Improve performance'; 
                }  
                use case 'Autonomous vehicle edge closer' : Mission  { 
                    @CapellaID { eid = "7b897d15-1677-4a57-acd5-258606bcd822"; } 
                }  
                use case 'Shorter Model Cycles' : Mission  { 
                    @CapellaID { eid = "9bbca8e9-d2ec-453f-bc08-552c4820d543"; } 
                    include 'eRod_Autonomous_Vehicle_2024 Project'::'eRod_Autonomous_Vehicle_2024'::'System Analysis'::'Capabilities'::'Quick solution for the issues'; 
                }  
                use case 'Better customer/driving experience in the car' : Mission  { 
                    @CapellaID { eid = "60a08eb4-caf2-4f0e-920e-e5aa6a952695"; } 
                    attribute :>> summary = "Improve driving experience e.g. sporty drive"; 
                    actor 'Driver' = 'eRod_Autonomous_Vehicle_2024 Project'::'eRod_Autonomous_Vehicle_2024'::'System Analysis'::'Structure'::'Driver'; 
                }  
                use case 'Security' : Mission  { 
                    @CapellaID { eid = "12eb9e26-d7bc-4215-a017-05b2ae4bec37"; } 
                }  
                use case 'Improve car buying experience' : Mission  { 
                    @CapellaID { eid = "7fe92b08-aa50-443e-8815-e021466c3e81"; } 
                }  
                use case 'Car Racing' : Mission  { 
                    @CapellaID { eid = "cc922bf1-afe8-465a-9925-443d26628037"; } 
                    attribute :>> summary = "eRod has also the capability to attend car racing"; 
                    actor 'Driver' = 'eRod_Autonomous_Vehicle_2024 Project'::'eRod_Autonomous_Vehicle_2024'::'System Analysis'::'Structure'::'Driver'; 
                    include 'eRod_Autonomous_Vehicle_2024 Project'::'eRod_Autonomous_Vehicle_2024'::'System Analysis'::'Capabilities'::'Sporty drive'; 
                    include 'eRod_Autonomous_Vehicle_2024 Project'::'eRod_Autonomous_Vehicle_2024'::'System Analysis'::'Capabilities'::'Finish race track'; 
                }  
                use case 'Provide Active Driver Assistance' : Mission  { 
                    @CapellaID { eid = "0fade19b-02d8-4f1e-b950-5b38b7ed2932"; } 
                    actor 'eRod' = 'eRod_Autonomous_Vehicle_2024 Project'::'eRod_Autonomous_Vehicle_2024'::'System Analysis'::'Structure'::'eRod'; 
                    actor 'Driver' = 'eRod_Autonomous_Vehicle_2024 Project'::'eRod_Autonomous_Vehicle_2024'::'System Analysis'::'Structure'::'Driver'; 
                    include 'eRod_Autonomous_Vehicle_2024 Project'::'eRod_Autonomous_Vehicle_2024'::'System Analysis'::'Capabilities'::'Maintain Distance to Lead Car'; 
                    include 'eRod_Autonomous_Vehicle_2024 Project'::'eRod_Autonomous_Vehicle_2024'::'System Analysis'::'Capabilities'::'Avoid Collision'; 
                    include 'eRod_Autonomous_Vehicle_2024 Project'::'eRod_Autonomous_Vehicle_2024'::'System Analysis'::'Capabilities'::'Driving Assistance'; 
                }  
            } 
            package  'Structure' {
                @PackageMeta {
                    type = "SystemComponentPkg";
                } 
                @CapellaID { eid = "a0eeb371-ab2d-470e-bfe5-59d98534f7d7"; } 
                part 'eRod' : SystemComponent { 
                    @CapellaID { eid = "8bf8c9cc-5079-435d-9c25-2aaa2a2d1ae1"; } 
                    attribute :>> isAbstract = false; 
                    attribute :>> isActor = false; 
                    attribute :>> isDataComponent = false; 
                    attribute :>> isHuman = false; 
                    allocation 'e42ed350-a886-4d28-842c-2bb05b65f735' : ComponentFunctionalAllocation
                        allocate function ::> 'eRod_Autonomous_Vehicle_2024 Project'::'eRod_Autonomous_Vehicle_2024'::'System Analysis'::'System Functions'::'Root System Function'.'Transfer Energy'.'Tranfer electrical energy into mechanical energy'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Transfer Energy'.'Tranfer electrical energy into mechanical energy' ; 
                    allocation 'a18e76d7-b0e4-4952-83dd-5b9193f66be9' : ComponentFunctionalAllocation
                        allocate function ::> 'eRod_Autonomous_Vehicle_2024 Project'::'eRod_Autonomous_Vehicle_2024'::'System Analysis'::'System Functions'::'Root System Function'.'Motor protect'.'Detect temperature limit'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Motor protect'.'Detect temperature limit' ; 
                    allocation '8d70d4e8-f4d5-4b7e-b665-82b5b9f10b00' : ComponentFunctionalAllocation
                        allocate function ::> 'eRod_Autonomous_Vehicle_2024 Project'::'eRod_Autonomous_Vehicle_2024'::'System Analysis'::'System Functions'::'Root System Function'.'Transfer Energy'.'Acquire Energy'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Transfer Energy'.'Acquire Energy' ; 
                    allocation 'b21d0fc4-29ea-41b8-b1a8-9883deeb8d83' : ComponentFunctionalAllocation
                        allocate function ::> 'eRod_Autonomous_Vehicle_2024 Project'::'eRod_Autonomous_Vehicle_2024'::'System Analysis'::'System Functions'::'Root System Function'.'Transfer Energy'.'Generate heat'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Transfer Energy'.'Generate heat' ; 
                    allocation '7d8f7ece-d753-4550-a0f5-23ea1cc8d654' : ComponentFunctionalAllocation
                        allocate function ::> 'eRod_Autonomous_Vehicle_2024 Project'::'eRod_Autonomous_Vehicle_2024'::'System Analysis'::'System Functions'::'Root System Function'.'Transfer Energy'.'generate power'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Transfer Energy'.'generate power' ; 
                    allocation '3e488eb4-369a-43a7-8c4a-2f49e983ab7c' : ComponentFunctionalAllocation
                        allocate function ::> 'eRod_Autonomous_Vehicle_2024 Project'::'eRod_Autonomous_Vehicle_2024'::'System Analysis'::'System Functions'::'Root System Function'.'Motor protect'.'Monitor temperature'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Motor protect'.'Monitor temperature' ; 
                    allocation 'ec90b63d-0815-4e15-844a-26612542bdba' : ComponentFunctionalAllocation
                        allocate function ::> 'eRod_Autonomous_Vehicle_2024 Project'::'eRod_Autonomous_Vehicle_2024'::'System Analysis'::'System Functions'::'Root System Function'.'Control temperature'.'Limit temperature'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Control temperature'.'Limit temperature' ; 
                    allocation '52ce3ab6-7780-4f61-981d-79984110fc72' : ComponentFunctionalAllocation
                        allocate function ::> 'eRod_Autonomous_Vehicle_2024 Project'::'eRod_Autonomous_Vehicle_2024'::'System Analysis'::'System Functions'::'Root System Function'.'Control temperature'.'Limit power'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Control temperature'.'Limit power' ; 
                    allocation 'f6d82108-5266-4340-9d71-17b0780ba495' : ComponentFunctionalAllocation
                        allocate function ::> 'eRod_Autonomous_Vehicle_2024 Project'::'eRod_Autonomous_Vehicle_2024'::'System Analysis'::'System Functions'::'Root System Function'.'Motor protect'.'Reduce power'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Motor protect'.'Reduce power' ; 
                    allocation 'a4c36e4d-e83f-474f-8c32-5f742e069873' : ComponentFunctionalAllocation
                        allocate function ::> 'eRod_Autonomous_Vehicle_2024 Project'::'eRod_Autonomous_Vehicle_2024'::'System Analysis'::'System Functions'::'Root System Function'.'Sporty drive'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Sporty drive' ; 
                    allocation 'b851bdfc-8de1-45f6-8f07-3deb63958aad' : ComponentFunctionalAllocation
                        allocate function ::> 'eRod_Autonomous_Vehicle_2024 Project'::'eRod_Autonomous_Vehicle_2024'::'System Analysis'::'System Functions'::'Root System Function'.'Deaccelerate'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Deaccelerate' ; 
                    allocation '95204533-b887-4d7f-ba62-ee97403a02a8' : ComponentFunctionalAllocation
                        allocate function ::> 'eRod_Autonomous_Vehicle_2024 Project'::'eRod_Autonomous_Vehicle_2024'::'System Analysis'::'System Functions'::'Root System Function'.'Stop'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Stop' ; 
                    allocation '5880ba57-4930-44bd-aebd-3233603f21ae' : ComponentFunctionalAllocation
                        allocate function ::> 'eRod_Autonomous_Vehicle_2024 Project'::'eRod_Autonomous_Vehicle_2024'::'System Analysis'::'System Functions'::'Root System Function'.'Motor overheating warning '
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Motor overheating warning ' ; 
                    allocation '4a8634e4-ea9c-4be5-b314-cf8ef75e52fd' : ComponentFunctionalAllocation
                        allocate function ::> 'eRod_Autonomous_Vehicle_2024 Project'::'eRod_Autonomous_Vehicle_2024'::'System Analysis'::'System Functions'::'Root System Function'.'Maintain distance'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Maintain distance' ; 
                    allocation 'df2f5df7-d4cc-4e81-bb22-6c69163e4e6a' : ComponentFunctionalAllocation
                        allocate function ::> 'eRod_Autonomous_Vehicle_2024 Project'::'eRod_Autonomous_Vehicle_2024'::'System Analysis'::'System Functions'::'Root System Function'.'Control braking'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Control braking' ; 
                    allocation '663308c6-dd27-482d-8f08-3f9b192c1e6f' : ComponentFunctionalAllocation
                        allocate function ::> 'eRod_Autonomous_Vehicle_2024 Project'::'eRod_Autonomous_Vehicle_2024'::'System Analysis'::'System Functions'::'Root System Function'.'Locate targets'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Locate targets' ; 
                    allocation 'b75803da-363a-4add-ad2b-8e88d6e9d322' : ComponentFunctionalAllocation
                        allocate function ::> 'eRod_Autonomous_Vehicle_2024 Project'::'eRod_Autonomous_Vehicle_2024'::'System Analysis'::'System Functions'::'Root System Function'.'Maintain speed'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Maintain speed' ; 
                    allocation '9c7726da-d596-4456-baef-bda8df991f93' : ComponentFunctionalAllocation
                        allocate function ::> 'eRod_Autonomous_Vehicle_2024 Project'::'eRod_Autonomous_Vehicle_2024'::'System Analysis'::'System Functions'::'Root System Function'.'Avoid collision'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Avoid collision' ; 
                    allocation 'b2e8934e-4d8e-41c2-b858-e828fe8c628a' : ComponentFunctionalAllocation
                        allocate function ::> 'eRod_Autonomous_Vehicle_2024 Project'::'eRod_Autonomous_Vehicle_2024'::'System Analysis'::'System Functions'::'Root System Function'.'Provide vehicle status'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Provide vehicle status' ; 
                    allocation '26ea1706-c402-4779-9bc9-774bf79bd4b9' : ComponentFunctionalAllocation
                        allocate function ::> 'eRod_Autonomous_Vehicle_2024 Project'::'eRod_Autonomous_Vehicle_2024'::'System Analysis'::'System Functions'::'Root System Function'.'Steer wheels'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Steer wheels' ; 
                    allocation '814bd85f-cc7b-46ad-8cc4-263408dfd04c' : ComponentFunctionalAllocation
                        allocate function ::> 'eRod_Autonomous_Vehicle_2024 Project'::'eRod_Autonomous_Vehicle_2024'::'System Analysis'::'System Functions'::'Root System Function'.'Automatic Steering'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Automatic Steering' ; 
                    allocation '39fb8a94-4f6b-4257-bd40-26dca6a39ca2' : ComponentFunctionalAllocation
                        allocate function ::> 'eRod_Autonomous_Vehicle_2024 Project'::'eRod_Autonomous_Vehicle_2024'::'System Analysis'::'System Functions'::'Root System Function'.'Detect road'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Detect road' ; 
                    allocation '51b36803-6894-47f2-a081-438d356f9703' : ComponentFunctionalAllocation
                        allocate function ::> 'eRod_Autonomous_Vehicle_2024 Project'::'eRod_Autonomous_Vehicle_2024'::'System Analysis'::'System Functions'::'Root System Function'.'Remote Operate Car'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Remote Operate Car' ; 
                    allocation 'baeb63c8-5378-4284-9df8-6a72d0f4bc33' : ComponentFunctionalAllocation
                        allocate function ::> 'eRod_Autonomous_Vehicle_2024 Project'::'eRod_Autonomous_Vehicle_2024'::'System Analysis'::'System Functions'::'Root System Function'.'Park vehicle'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Park vehicle' ; 
                    allocation '60c2eb12-3da4-486d-9d41-21325c3f912e' : ComponentFunctionalAllocation
                        allocate function ::> 'eRod_Autonomous_Vehicle_2024 Project'::'eRod_Autonomous_Vehicle_2024'::'System Analysis'::'System Functions'::'Root System Function'.'Steer Wheels Remote'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Steer Wheels Remote' ; 
                    allocation '9ff79451-c5fc-47ab-b2bd-2643ee858412' : ComponentFunctionalAllocation
                        allocate function ::> 'eRod_Autonomous_Vehicle_2024 Project'::'eRod_Autonomous_Vehicle_2024'::'System Analysis'::'System Functions'::'Root System Function'.'Status and command indication'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Status and command indication' ; 
                    allocation 'dc82c8a3-a496-46f4-a5a6-559f6d33a5c5' : ComponentFunctionalAllocation
                        allocate function ::> 'eRod_Autonomous_Vehicle_2024 Project'::'eRod_Autonomous_Vehicle_2024'::'System Analysis'::'System Functions'::'Root System Function'.'Deliver traction to surface'
                        to component ::> 'eRod_Autonomous_Vehicle_2024 Project'::'eRod_Autonomous_Vehicle_2024'::'System Analysis'::'Structure'::'eRod';
                    perform 'eRod_Autonomous_Vehicle_2024 Project'::'eRod_Autonomous_Vehicle_2024'::'System Analysis'::'System Functions'::'Root System Function'.'Deliver traction to surface' ; 
                    state 'System State Machine' : StateMachine  { 
                        @CapellaID { eid = "9134ec88-480f-4015-af4b-2089d1c9862f"; } 
                        attribute :>> isControlOperator = false; 
                    }  
                    ref :>> ownedFunctionalAllocation =  ('eRod_Autonomous_Vehicle_2024 Project'::'eRod_Autonomous_Vehicle_2024'::'System Analysis'::'Structure'::'eRod'.'e42ed350-a886-4d28-842c-2bb05b65f735',
                    'eRod_Autonomous_Vehicle_2024 Project'::'eRod_Autonomous_Vehicle_2024'::'System Analysis'::'Structure'::'eRod'.'a18e76d7-b0e4-4952-83dd-5b9193f66be9',
                    'eRod_Autonomous_Vehicle_2024 Project'::'eRod_Autonomous_Vehicle_2024'::'System Analysis'::'Structure'::'eRod'.'8d70d4e8-f4d5-4b7e-b665-82b5b9f10b00',
                    'eRod_Autonomous_Vehicle_2024 Project'::'eRod_Autonomous_Vehicle_2024'::'System Analysis'::'Structure'::'eRod'.'b21d0fc4-29ea-41b8-b1a8-9883deeb8d83',
                    'eRod_Autonomous_Vehicle_2024 Project'::'eRod_Autonomous_Vehicle_2024'::'System Analysis'::'Structure'::'eRod'.'7d8f7ece-d753-4550-a0f5-23ea1cc8d654',
                    'eRod_Autonomous_Vehicle_2024 Project'::'eRod_Autonomous_Vehicle_2024'::'System Analysis'::'Structure'::'eRod'.'3e488eb4-369a-43a7-8c4a-2f49e983ab7c',
                    'eRod_Autonomous_Vehicle_2024 Project'::'eRod_Autonomous_Vehicle_2024'::'System Analysis'::'Structure'::'eRod'.'ec90b63d-0815-4e15-844a-26612542bdba',
                    'eRod_Autonomous_Vehicle_2024 Project'::'eRod_Autonomous_Vehicle_2024'::'System Analysis'::'Structure'::'eRod'.'52ce3ab6-7780-4f61-981d-79984110fc72',
                    'eRod_Autonomous_Vehicle_2024 Project'::'eRod_Autonomous_Vehicle_2024'::'System Analysis'::'Structure'::'eRod'.'f6d82108-5266-4340-9d71-17b0780ba495',
                    'eRod_Autonomous_Vehicle_2024 Project'::'eRod_Autonomous_Vehicle_2024'::'System Analysis'::'Structure'::'eRod'.'a4c36e4d-e83f-474f-8c32-5f742e069873',
                    'eRod_Autonomous_Vehicle_2024 Project'::'eRod_Autonomous_Vehicle_2024'::'System Analysis'::'Structure'::'eRod'.'b851bdfc-8de1-45f6-8f07-3deb63958aad',
                    'eRod_Autonomous_Vehicle_2024 Project'::'eRod_Autonomous_Vehicle_2024'::'System Analysis'::'Structure'::'eRod'.'95204533-b887-4d7f-ba62-ee97403a02a8',
                    'eRod_Autonomous_Vehicle_2024 Project'::'eRod_Autonomous_Vehicle_2024'::'System Analysis'::'Structure'::'eRod'.'5880ba57-4930-44bd-aebd-3233603f21ae',
                    'eRod_Autonomous_Vehicle_2024 Project'::'eRod_Autonomous_Vehicle_2024'::'System Analysis'::'Structure'::'eRod'.'4a8634e4-ea9c-4be5-b314-cf8ef75e52fd',
                    'eRod_Autonomous_Vehicle_2024 Project'::'eRod_Autonomous_Vehicle_2024'::'System Analysis'::'Structure'::'eRod'.'df2f5df7-d4cc-4e81-bb22-6c69163e4e6a',
                    'eRod_Autonomous_Vehicle_2024 Project'::'eRod_Autonomous_Vehicle_2024'::'System Analysis'::'Structure'::'eRod'.'663308c6-dd27-482d-8f08-3f9b192c1e6f',
                    'eRod_Autonomous_Vehicle_2024 Project'::'eRod_Autonomous_Vehicle_2024'::'System Analysis'::'Structure'::'eRod'.'b75803da-363a-4add-ad2b-8e88d6e9d322',
                    'eRod_Autonomous_Vehicle_2024 Project'::'eRod_Autonomous_Vehicle_2024'::'System Analysis'::'Structure'::'eRod'.'9c7726da-d596-4456-baef-bda8df991f93',
                    'eRod_Autonomous_Vehicle_2024 Project'::'eRod_Autonomous_Vehicle_2024'::'System Analysis'::'Structure'::'eRod'.'b2e8934e-4d8e-41c2-b858-e828fe8c628a',
                    'eRod_Autonomous_Vehicle_2024 Project'::'eRod_Autonomous_Vehicle_2024'::'System Analysis'::'Structure'::'eRod'.'26ea1706-c402-4779-9bc9-774bf79bd4b9',
                    'eRod_Autonomous_Vehicle_2024 Project'::'eRod_Autonomous_Vehicle_2024'::'System Analysis'::'Structure'::'eRod'.'814bd85f-cc7b-46ad-8cc4-263408dfd04c',
                    'eRod_Autonomous_Vehicle_2024 Project'::'eRod_Autonomous_Vehicle_2024'::'System Analysis'::'Structure'::'eRod'.'39fb8a94-4f6b-4257-bd40-26dca6a39ca2',
                    'eRod_Autonomous_Vehicle_2024 Project'::'eRod_Autonomous_Vehicle_2024'::'System Analysis'::'Structure'::'eRod'.'51b36803-6894-47f2-a081-438d356f9703',
                    'eRod_Autonomous_Vehicle_2024 Project'::'eRod_Autonomous_Vehicle_2024'::'System Analysis'::'Structure'::'eRod'.'baeb63c8-5378-4284-9df8-6a72d0f4bc33',
                    'eRod_Autonomous_Vehicle_2024 Project'::'eRod_Autonomous_Vehicle_2024'::'System Analysis'::'Structure'::'eRod'.'60c2eb12-3da4-486d-9d41-21325c3f912e',
                    'eRod_Autonomous_Vehicle_2024 Project'::'eRod_Autonomous_Vehicle_2024'::'System Analysis'::'Structure'::'eRod'.'9ff79451-c5fc-47ab-b2bd-2643ee858412',
                    'eRod_Autonomous_Vehicle_2024 Project'::'eRod_Autonomous_Vehicle_2024'::'System Analysis'::'Structure'::'eRod'.'dc82c8a3-a496-46f4-a5a6-559f6d33a5c5'); 
                    ref :>> ownedStateMachines =  ('eRod_Autonomous_Vehicle_2024 Project'::'eRod_Autonomous_Vehicle_2024'::'System Analysis'::'Structure'::'eRod'.'System State Machine'); 
                }  
                part 'Driver' : SystemComponent { 
                    @CapellaID { eid = "f6e2e1ed-849f-4f0f-bec3-e0abc4f30a6c"; } 
                    attribute :>> isAbstract = false; 
                    attribute :>> isActor = true; 
                    attribute :>> isDataComponent = false; 
                    attribute :>> isHuman = true; 
                    allocation 'fb3723f6-2850-4408-b553-dbb64caddaff' : ComponentFunctionalAllocation
                        allocate function ::> 'eRod_Autonomous_Vehicle_2024 Project'::'eRod_Autonomous_Vehicle_2024'::'System Analysis'::'System Functions'::'Root System Function'.'Drive on a race track'
                        to component ::> 'eRod_Autonomous_Vehicle_2024 Project'::'eRod_Autonomous_Vehicle_2024'::'System Analysis'::'Structure'::'Driver';
                    perform 'eRod_Autonomous_Vehicle_2024 Project'::'eRod_Autonomous_Vehicle_2024'::'System Analysis'::'System Functions'::'Root System Function'.'Drive on a race track' ; 
                    allocation 'd5a029ba-82eb-4db3-9c9b-5494fccbf86e' : ComponentFunctionalAllocation
                        allocate function ::> 'eRod_Autonomous_Vehicle_2024 Project'::'eRod_Autonomous_Vehicle_2024'::'System Analysis'::'System Functions'::'Root System Function'.'Car racing experience absorbed'
                        to component ::> 'eRod_Autonomous_Vehicle_2024 Project'::'eRod_Autonomous_Vehicle_2024'::'System Analysis'::'Structure'::'Driver';
                    perform 'eRod_Autonomous_Vehicle_2024 Project'::'eRod_Autonomous_Vehicle_2024'::'System Analysis'::'System Functions'::'Root System Function'.'Car racing experience absorbed' ; 
                    allocation 'a0dd425a-b576-432d-be7f-629457f13ef9' : ComponentFunctionalAllocation
                        allocate function ::> 'eRod_Autonomous_Vehicle_2024 Project'::'eRod_Autonomous_Vehicle_2024'::'System Analysis'::'System Functions'::'Root System Function'.'Report issues'
                        to component ::> 'eRod_Autonomous_Vehicle_2024 Project'::'eRod_Autonomous_Vehicle_2024'::'System Analysis'::'Structure'::'Driver';
                    perform 'eRod_Autonomous_Vehicle_2024 Project'::'eRod_Autonomous_Vehicle_2024'::'System Analysis'::'System Functions'::'Root System Function'.'Report issues' ; 
                    allocation 'a56cad70-367a-470d-b1b5-4058fc6d8466' : ComponentFunctionalAllocation
                        allocate function ::> 'eRod_Autonomous_Vehicle_2024 Project'::'eRod_Autonomous_Vehicle_2024'::'System Analysis'::'System Functions'::'Root System Function'.'Get informed with issues'
                        to component ::> 'eRod_Autonomous_Vehicle_2024 Project'::'eRod_Autonomous_Vehicle_2024'::'System Analysis'::'Structure'::'Driver';
                    perform 'eRod_Autonomous_Vehicle_2024 Project'::'eRod_Autonomous_Vehicle_2024'::'System Analysis'::'System Functions'::'Root System Function'.'Get informed with issues' ; 
                    allocation '28c5bb8b-d715-4dc6-94f5-fd7be7c842d0' : ComponentFunctionalAllocation
                        allocate function ::> 'eRod_Autonomous_Vehicle_2024 Project'::'eRod_Autonomous_Vehicle_2024'::'System Analysis'::'System Functions'::'Root System Function'.'Get Software-update'
                        to component ::> 'eRod_Autonomous_Vehicle_2024 Project'::'eRod_Autonomous_Vehicle_2024'::'System Analysis'::'Structure'::'Driver';
                    perform 'eRod_Autonomous_Vehicle_2024 Project'::'eRod_Autonomous_Vehicle_2024'::'System Analysis'::'System Functions'::'Root System Function'.'Get Software-update' ; 
                    allocation '64e924e1-f657-47db-a591-31a28fca3fad' : ComponentFunctionalAllocation
                        allocate function ::> 'eRod_Autonomous_Vehicle_2024 Project'::'eRod_Autonomous_Vehicle_2024'::'System Analysis'::'System Functions'::'Root System Function'.'Obtain car racing experience'
                        to component ::> 'eRod_Autonomous_Vehicle_2024 Project'::'eRod_Autonomous_Vehicle_2024'::'System Analysis'::'Structure'::'Driver';
                    perform 'eRod_Autonomous_Vehicle_2024 Project'::'eRod_Autonomous_Vehicle_2024'::'System Analysis'::'System Functions'::'Root System Function'.'Obtain car racing experience' ; 
                    allocation 'c320a8e3-7ec9-4ef0-b5ed-a5d1468207a2' : ComponentFunctionalAllocation
                        allocate function ::> 'eRod_Autonomous_Vehicle_2024 Project'::'eRod_Autonomous_Vehicle_2024'::'System Analysis'::'System Functions'::'Root System Function'.'Drive vehicle'
                        to component ::> 'eRod_Autonomous_Vehicle_2024 Project'::'eRod_Autonomous_Vehicle_2024'::'System Analysis'::'Structure'::'Driver';
                    perform 'eRod_Autonomous_Vehicle_2024 Project'::'eRod_Autonomous_Vehicle_2024'::'System Analysis'::'System Functions'::'Root System Function'.'Drive vehicle' ; 
                    allocation '808dd07e-fcd3-43c4-b6ca-72afbeb25a1a' : ComponentFunctionalAllocation
                        allocate function ::> 'eRod_Autonomous_Vehicle_2024 Project'::'eRod_Autonomous_Vehicle_2024'::'System Analysis'::'System Functions'::'Root System Function'.'Observe status'
                        to component ::> 'eRod_Autonomous_Vehicle_2024 Project'::'eRod_Autonomous_Vehicle_2024'::'System Analysis'::'Structure'::'Driver';
                    perform 'eRod_Autonomous_Vehicle_2024 Project'::'eRod_Autonomous_Vehicle_2024'::'System Analysis'::'System Functions'::'Root System Function'.'Observe status' ; 
                    port 'CP 1' : ComponentPort { 
                        @CapellaID { eid = "3d939124-5ae7-4d89-b2db-46851687b2f4"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                    }  
                    port 'CP 2' : ComponentPort { 
                        @CapellaID { eid = "8e89340c-fcd7-4a35-a90c-f5786a568d43"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                    }  
                    port 'CP 3' : ComponentPort { 
                        @CapellaID { eid = "1c2ec86d-e485-420a-bfbc-7b14a2e53471"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                    }  
                    ref :>> ownedFunctionalAllocation =  ('eRod_Autonomous_Vehicle_2024 Project'::'eRod_Autonomous_Vehicle_2024'::'System Analysis'::'Structure'::'Driver'.'fb3723f6-2850-4408-b553-dbb64caddaff',
                    'eRod_Autonomous_Vehicle_2024 Project'::'eRod_Autonomous_Vehicle_2024'::'System Analysis'::'Structure'::'Driver'.'d5a029ba-82eb-4db3-9c9b-5494fccbf86e',
                    'eRod_Autonomous_Vehicle_2024 Project'::'eRod_Autonomous_Vehicle_2024'::'System Analysis'::'Structure'::'Driver'.'a0dd425a-b576-432d-be7f-629457f13ef9',
                    'eRod_Autonomous_Vehicle_2024 Project'::'eRod_Autonomous_Vehicle_2024'::'System Analysis'::'Structure'::'Driver'.'a56cad70-367a-470d-b1b5-4058fc6d8466',
                    'eRod_Autonomous_Vehicle_2024 Project'::'eRod_Autonomous_Vehicle_2024'::'System Analysis'::'Structure'::'Driver'.'28c5bb8b-d715-4dc6-94f5-fd7be7c842d0',
                    'eRod_Autonomous_Vehicle_2024 Project'::'eRod_Autonomous_Vehicle_2024'::'System Analysis'::'Structure'::'Driver'.'64e924e1-f657-47db-a591-31a28fca3fad',
                    'eRod_Autonomous_Vehicle_2024 Project'::'eRod_Autonomous_Vehicle_2024'::'System Analysis'::'Structure'::'Driver'.'c320a8e3-7ec9-4ef0-b5ed-a5d1468207a2',
                    'eRod_Autonomous_Vehicle_2024 Project'::'eRod_Autonomous_Vehicle_2024'::'System Analysis'::'Structure'::'Driver'.'808dd07e-fcd3-43c4-b6ca-72afbeb25a1a'); 
                     
                     
                }  
                part 'Sport-Offroad Buggies' : SystemComponent { 
                    @CapellaID { eid = "4b9fa959-b0a9-41c6-b57f-1cf8dc4581aa"; } 
                    attribute :>> isAbstract = false; 
                    attribute :>> isActor = true; 
                    attribute :>> isDataComponent = false; 
                    attribute :>> isHuman = false; 
                     
                }  
                part 'eRod Manufactor' : SystemComponent { 
                    @CapellaID { eid = "b6d6d2b9-bbfb-4def-baa2-fa9e6d071e15"; } 
                    attribute :>> isAbstract = false; 
                    attribute :>> isActor = true; 
                    attribute :>> isDataComponent = false; 
                    attribute :>> isHuman = true; 
                    allocation '161e6fd0-0419-41ef-94fd-ca2ea70dd491' : ComponentFunctionalAllocation
                        allocate function ::> 'eRod_Autonomous_Vehicle_2024 Project'::'eRod_Autonomous_Vehicle_2024'::'System Analysis'::'System Functions'::'Root System Function'.'Recieve feedback'
                        to component ::> 'eRod_Autonomous_Vehicle_2024 Project'::'eRod_Autonomous_Vehicle_2024'::'System Analysis'::'Structure'::'eRod Manufactor';
                    perform 'eRod_Autonomous_Vehicle_2024 Project'::'eRod_Autonomous_Vehicle_2024'::'System Analysis'::'System Functions'::'Root System Function'.'Recieve feedback' ; 
                    allocation 'b060b9e6-11f4-4182-a014-607fa3698774' : ComponentFunctionalAllocation
                        allocate function ::> 'eRod_Autonomous_Vehicle_2024 Project'::'eRod_Autonomous_Vehicle_2024'::'System Analysis'::'System Functions'::'Root System Function'.'Provide solution'
                        to component ::> 'eRod_Autonomous_Vehicle_2024 Project'::'eRod_Autonomous_Vehicle_2024'::'System Analysis'::'Structure'::'eRod Manufactor';
                    perform 'eRod_Autonomous_Vehicle_2024 Project'::'eRod_Autonomous_Vehicle_2024'::'System Analysis'::'System Functions'::'Root System Function'.'Provide solution' ; 
                    port 'CP 1' : ComponentPort { 
                        @CapellaID { eid = "7e71b4c2-ae30-4c79-ab6e-de0d76bdf247"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                    }  
                    port 'CP 2' : ComponentPort { 
                        @CapellaID { eid = "b4fe137b-0b43-4cbb-b66e-48b8ce367bb6"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                    }  
                    ref :>> ownedFunctionalAllocation =  ('eRod_Autonomous_Vehicle_2024 Project'::'eRod_Autonomous_Vehicle_2024'::'System Analysis'::'Structure'::'eRod Manufactor'.'161e6fd0-0419-41ef-94fd-ca2ea70dd491',
                    'eRod_Autonomous_Vehicle_2024 Project'::'eRod_Autonomous_Vehicle_2024'::'System Analysis'::'Structure'::'eRod Manufactor'.'b060b9e6-11f4-4182-a014-607fa3698774'); 
                     
                     
                }  
                part 'Road' : SystemComponent { 
                    @CapellaID { eid = "eeb2d5b3-16b1-47e4-a213-a4377751d7e3"; } 
                    attribute :>> isAbstract = false; 
                    attribute :>> isActor = true; 
                    attribute :>> isDataComponent = false; 
                    attribute :>> isHuman = false; 
                    allocation '7553e709-3acb-4ead-bcdd-8bf07751e253' : ComponentFunctionalAllocation
                        allocate function ::> 'eRod_Autonomous_Vehicle_2024 Project'::'eRod_Autonomous_Vehicle_2024'::'System Analysis'::'System Functions'::'Root System Function'.'Provide road markers'
                        to component ::> 'eRod_Autonomous_Vehicle_2024 Project'::'eRod_Autonomous_Vehicle_2024'::'System Analysis'::'Structure'::'Road';
                    perform 'eRod_Autonomous_Vehicle_2024 Project'::'eRod_Autonomous_Vehicle_2024'::'System Analysis'::'System Functions'::'Root System Function'.'Provide road markers' ; 
                    allocation '9edd74f2-3c4f-4432-b833-fec8c5e0fcc7' : ComponentFunctionalAllocation
                        allocate function ::> 'eRod_Autonomous_Vehicle_2024 Project'::'eRod_Autonomous_Vehicle_2024'::'System Analysis'::'System Functions'::'Root System Function'.'Resist Front Wheels'
                        to component ::> 'eRod_Autonomous_Vehicle_2024 Project'::'eRod_Autonomous_Vehicle_2024'::'System Analysis'::'Structure'::'Road';
                    perform 'eRod_Autonomous_Vehicle_2024 Project'::'eRod_Autonomous_Vehicle_2024'::'System Analysis'::'System Functions'::'Root System Function'.'Resist Front Wheels' ; 
                    ref :>> ownedFunctionalAllocation =  ('eRod_Autonomous_Vehicle_2024 Project'::'eRod_Autonomous_Vehicle_2024'::'System Analysis'::'Structure'::'Road'.'7553e709-3acb-4ead-bcdd-8bf07751e253',
                    'eRod_Autonomous_Vehicle_2024 Project'::'eRod_Autonomous_Vehicle_2024'::'System Analysis'::'Structure'::'Road'.'9edd74f2-3c4f-4432-b833-fec8c5e0fcc7'); 
                }  
                part 'Target Vehicle' : SystemComponent { 
                    @CapellaID { eid = "e5ab1df1-608a-4912-a67d-7fe59546aad5"; } 
                    attribute :>> isAbstract = false; 
                    attribute :>> isActor = true; 
                    attribute :>> isDataComponent = false; 
                    attribute :>> isHuman = false; 
                    allocation '1067e10d-34cb-433f-8ae5-4d5bcaadef26' : ComponentFunctionalAllocation
                        allocate function ::> 'eRod_Autonomous_Vehicle_2024 Project'::'eRod_Autonomous_Vehicle_2024'::'System Analysis'::'System Functions'::'Root System Function'.'Provide target vehicle velocity'
                        to component ::> 'eRod_Autonomous_Vehicle_2024 Project'::'eRod_Autonomous_Vehicle_2024'::'System Analysis'::'Structure'::'Target Vehicle';
                    perform 'eRod_Autonomous_Vehicle_2024 Project'::'eRod_Autonomous_Vehicle_2024'::'System Analysis'::'System Functions'::'Root System Function'.'Provide target vehicle velocity' ; 
                    ref :>> ownedFunctionalAllocation =  ('eRod_Autonomous_Vehicle_2024 Project'::'eRod_Autonomous_Vehicle_2024'::'System Analysis'::'Structure'::'Target Vehicle'.'1067e10d-34cb-433f-8ae5-4d5bcaadef26'); 
                }  
                part 'Weather' : SystemComponent { 
                    @CapellaID { eid = "301fac4d-b472-46b7-a299-e00bd33a33f5"; } 
                    attribute :>> isAbstract = false; 
                    attribute :>> isActor = true; 
                    attribute :>> isDataComponent = false; 
                    attribute :>> isHuman = false; 
                    allocation 'c8d5c0b7-3ace-44c7-998d-e13a630609fd' : ComponentFunctionalAllocation
                        allocate function ::> 'eRod_Autonomous_Vehicle_2024 Project'::'eRod_Autonomous_Vehicle_2024'::'System Analysis'::'System Functions'::'Root System Function'.'Provide weather'
                        to component ::> 'eRod_Autonomous_Vehicle_2024 Project'::'eRod_Autonomous_Vehicle_2024'::'System Analysis'::'Structure'::'Weather';
                    perform 'eRod_Autonomous_Vehicle_2024 Project'::'eRod_Autonomous_Vehicle_2024'::'System Analysis'::'System Functions'::'Root System Function'.'Provide weather' ; 
                    ref :>> ownedFunctionalAllocation =  ('eRod_Autonomous_Vehicle_2024 Project'::'eRod_Autonomous_Vehicle_2024'::'System Analysis'::'Structure'::'Weather'.'c8d5c0b7-3ace-44c7-998d-e13a630609fd'); 
                     
                     
                }  
                part 'Environment' : SystemComponent { 
                    @CapellaID { eid = "570cacff-244a-42f8-b1e7-b1289da1252f"; } 
                    attribute :>> isAbstract = false; 
                    attribute :>> isActor = true; 
                    attribute :>> isDataComponent = false; 
                    attribute :>> isHuman = false; 
                    part 'Terrain/Roads' : SystemComponent { 
                        @CapellaID { eid = "27a6cce0-8987-4317-8e9c-46b0c63d2dca"; } 
                        attribute :>> isAbstract = false; 
                        attribute :>> isActor = true; 
                        attribute :>> isDataComponent = false; 
                        attribute :>> isHuman = false; 
                        allocation 'db93ba36-7b40-4ed2-af2d-2180780dfffa' : ComponentFunctionalAllocation
                            allocate function ::> 'eRod_Autonomous_Vehicle_2024 Project'::'eRod_Autonomous_Vehicle_2024'::'System Analysis'::'System Functions'::'Root System Function'.'Provide diverse terrain'
                            to component ::> 'eRod_Autonomous_Vehicle_2024 Project'::'eRod_Autonomous_Vehicle_2024'::'System Analysis'::'Structure'::'Environment'.'Terrain/Roads';
                        perform 'eRod_Autonomous_Vehicle_2024 Project'::'eRod_Autonomous_Vehicle_2024'::'System Analysis'::'System Functions'::'Root System Function'.'Provide diverse terrain' ; 
                        allocation '0f61b85a-e3b3-4dd0-85fb-3e72b71cc690' : ComponentFunctionalAllocation
                            allocate function ::> 'eRod_Autonomous_Vehicle_2024 Project'::'eRod_Autonomous_Vehicle_2024'::'System Analysis'::'System Functions'::'Root System Function'.'Provide parking location'
                            to component ::> 'eRod_Autonomous_Vehicle_2024 Project'::'eRod_Autonomous_Vehicle_2024'::'System Analysis'::'Structure'::'Environment'.'Terrain/Roads';
                        perform 'eRod_Autonomous_Vehicle_2024 Project'::'eRod_Autonomous_Vehicle_2024'::'System Analysis'::'System Functions'::'Root System Function'.'Provide parking location' ; 
                        ref :>> ownedFunctionalAllocation =  ('eRod_Autonomous_Vehicle_2024 Project'::'eRod_Autonomous_Vehicle_2024'::'System Analysis'::'Structure'::'Environment'.'Terrain/Roads'.'db93ba36-7b40-4ed2-af2d-2180780dfffa',
                        'eRod_Autonomous_Vehicle_2024 Project'::'eRod_Autonomous_Vehicle_2024'::'System Analysis'::'Structure'::'Environment'.'Terrain/Roads'.'0f61b85a-e3b3-4dd0-85fb-3e72b71cc690'); 
                         
                         
                    }  
                    part 'External Objects' : SystemComponent { 
                        @CapellaID { eid = "6590b5ff-afcb-4c5c-ad80-4601b0f52d35"; } 
                        attribute :>> isAbstract = false; 
                        attribute :>> isActor = true; 
                        attribute :>> isDataComponent = false; 
                        attribute :>> isHuman = false; 
                        allocation '972795bb-7675-4944-b9d0-a9739f0ee450' : ComponentFunctionalAllocation
                            allocate function ::> 'eRod_Autonomous_Vehicle_2024 Project'::'eRod_Autonomous_Vehicle_2024'::'System Analysis'::'System Functions'::'Root System Function'.'Provide object location'
                            to component ::> 'eRod_Autonomous_Vehicle_2024 Project'::'eRod_Autonomous_Vehicle_2024'::'System Analysis'::'Structure'::'Environment'.'External Objects';
                        perform 'eRod_Autonomous_Vehicle_2024 Project'::'eRod_Autonomous_Vehicle_2024'::'System Analysis'::'System Functions'::'Root System Function'.'Provide object location' ; 
                        ref :>> ownedFunctionalAllocation =  ('eRod_Autonomous_Vehicle_2024 Project'::'eRod_Autonomous_Vehicle_2024'::'System Analysis'::'Structure'::'Environment'.'External Objects'.'972795bb-7675-4944-b9d0-a9739f0ee450'); 
                         
                    }  
                    ref :>> ownedSystemComponents =  ('eRod_Autonomous_Vehicle_2024 Project'::'eRod_Autonomous_Vehicle_2024'::'System Analysis'::'Structure'::'Environment'.'Terrain/Roads',
                    'eRod_Autonomous_Vehicle_2024 Project'::'eRod_Autonomous_Vehicle_2024'::'System Analysis'::'Structure'::'Environment'.'External Objects'); 
                     
                }  
                part 'Remote Driver' : SystemComponent { 
                    @CapellaID { eid = "6de87f9a-6404-46b5-adb3-a1bc61716117"; } 
                    attribute :>> isAbstract = false; 
                    attribute :>> isActor = true; 
                    attribute :>> isDataComponent = false; 
                    attribute :>> isHuman = true; 
                    allocation 'c61d2d77-9755-49f9-a992-887440a0b163' : ComponentFunctionalAllocation
                        allocate function ::> 'eRod_Autonomous_Vehicle_2024 Project'::'eRod_Autonomous_Vehicle_2024'::'System Analysis'::'System Functions'::'Root System Function'.'Vehicle Command'
                        to component ::> 'eRod_Autonomous_Vehicle_2024 Project'::'eRod_Autonomous_Vehicle_2024'::'System Analysis'::'Structure'::'Remote Driver';
                    perform 'eRod_Autonomous_Vehicle_2024 Project'::'eRod_Autonomous_Vehicle_2024'::'System Analysis'::'System Functions'::'Root System Function'.'Vehicle Command' ; 
                    allocation '1c45ab2f-985f-4a05-94a2-111c094b6f77' : ComponentFunctionalAllocation
                        allocate function ::> 'eRod_Autonomous_Vehicle_2024 Project'::'eRod_Autonomous_Vehicle_2024'::'System Analysis'::'System Functions'::'Root System Function'.'Receive Status of Progess '
                        to component ::> 'eRod_Autonomous_Vehicle_2024 Project'::'eRod_Autonomous_Vehicle_2024'::'System Analysis'::'Structure'::'Remote Driver';
                    perform 'eRod_Autonomous_Vehicle_2024 Project'::'eRod_Autonomous_Vehicle_2024'::'System Analysis'::'System Functions'::'Root System Function'.'Receive Status of Progess ' ; 
                    ref :>> ownedFunctionalAllocation =  ('eRod_Autonomous_Vehicle_2024 Project'::'eRod_Autonomous_Vehicle_2024'::'System Analysis'::'Structure'::'Remote Driver'.'c61d2d77-9755-49f9-a992-887440a0b163',
                    'eRod_Autonomous_Vehicle_2024 Project'::'eRod_Autonomous_Vehicle_2024'::'System Analysis'::'Structure'::'Remote Driver'.'1c45ab2f-985f-4a05-94a2-111c094b6f77'); 
                     
                }  
                interface '46011174-a12d-4b2d-a0bf-e5f67c207a77' : ComponentExchange 
                    connect source ::> 'eRod_Autonomous_Vehicle_2024 Project'::'eRod_Autonomous_Vehicle_2024'::'System Analysis'::'Structure'::'eRod Manufactor'.'CP 1'
                    to  target ::> 'eRod_Autonomous_Vehicle_2024 Project'::'eRod_Autonomous_Vehicle_2024'::'System Analysis'::'Structure'::'Driver'.'CP 3' { 
                    @CapellaID { eid = "46011174-a12d-4b2d-a0bf-e5f67c207a77"; } 
                    attribute :>> kind = ComponentExchangeKind::FLOW; 
                    attribute :>> interfaceName = "Feedback"; 
                    attribute :>> isOriented = false; 
                }  
            } 
        } 
        package  'Logical Architecture' {
            @PackageMeta {
                type = "LogicalArchitecture";
            } 
            @CapellaID { eid = "fb1689e4-638a-4a5f-aeba-c4d6781c3fa1"; } 
            package  'Logical Functions' {
                @PackageMeta {
                    type = "LogicalFunctionPkg";
                } 
                @CapellaID { eid = "00dd8e66-b147-4500-b353-10a491514aab"; } 
                action 'Root Logical Function' : LogicalFunction  { 
                    @CapellaID { eid = "594e16d2-1b78-4b5f-8644-053277bf9b6e"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> kind = FunctionKind::FUNCTION; 
                    attribute :>> isMaxInclusive = false; 
                    attribute :>> isMinInclusive = false; 
                    attribute :>> isOrdered = false; 
                    attribute :>> isUnique = false; 
                    action 'Drive on Track' : FunctionalChain  { 
                        @CapellaID { eid = "f9deebea-9f78-4262-a36d-56f37cd217c6"; } 
                        attribute :>> kind = FunctionalChainKind::SIMPLE; 
                        ref action 'a4fb1bd5-f51e-4575-94b3-58f990b8ba36' = 'eRod_Autonomous_Vehicle_2024 Project'::'eRod_Autonomous_Vehicle_2024'::'Logical Architecture'::'Logical Functions'::'Root Logical Function'.'Drive on a race track'; 
                        connection 'c6181fff-f161-492a-93c4-d45e60c2d706' : FunctionalChainInvolvementLink 
                            connect source ::> 'eRod_Autonomous_Vehicle_2024 Project'::'eRod_Autonomous_Vehicle_2024'::'Logical Architecture'::'Logical Functions'::'Root Logical Function'.'Drive on Track'.'a4fb1bd5-f51e-4575-94b3-58f990b8ba36'
                            to  target ::> 'eRod_Autonomous_Vehicle_2024 Project'::'eRod_Autonomous_Vehicle_2024'::'Logical Architecture'::'Logical Functions'::'Root Logical Function'.'Drive on Track'.'cfdf6ef7-9f44-4b9d-904e-f4b4709650d2' {

                                ref :>> involved = 'eRod_Autonomous_Vehicle_2024 Project'::'eRod_Autonomous_Vehicle_2024'::'Logical Architecture'::'Logical Functions'::'Root Logical Function'.'d83bfe14-3bb0-443f-8b64-ac175f2b9aa1';

                            } 
                        ref action 'cfdf6ef7-9f44-4b9d-904e-f4b4709650d2' = 'eRod_Autonomous_Vehicle_2024 Project'::'eRod_Autonomous_Vehicle_2024'::'Logical Architecture'::'Logical Functions'::'Root Logical Function'.'Motor Start'; 
                        connection 'c594062c-df08-42eb-9c8f-df1f347bf982' : FunctionalChainInvolvementLink 
                            connect source ::> 'eRod_Autonomous_Vehicle_2024 Project'::'eRod_Autonomous_Vehicle_2024'::'Logical Architecture'::'Logical Functions'::'Root Logical Function'.'Drive on Track'.'cfdf6ef7-9f44-4b9d-904e-f4b4709650d2'
                            to  target ::> 'eRod_Autonomous_Vehicle_2024 Project'::'eRod_Autonomous_Vehicle_2024'::'Logical Architecture'::'Logical Functions'::'Root Logical Function'.'Drive on Track'.'f8947e49-00c9-4657-9867-4d8132a383df' {

                                ref :>> involved = 'eRod_Autonomous_Vehicle_2024 Project'::'eRod_Autonomous_Vehicle_2024'::'Logical Architecture'::'Logical Functions'::'Root Logical Function'.'37640148-3029-4dd4-98be-abe69563435f';

                            } 
                        ref action 'f8947e49-00c9-4657-9867-4d8132a383df' = 'eRod_Autonomous_Vehicle_2024 Project'::'eRod_Autonomous_Vehicle_2024'::'Logical Architecture'::'Logical Functions'::'Root Logical Function'.'Transfer Energy'.'Acquire electrical Energy'; 
                        connection '55d780e9-f08a-4719-8329-30cbd4019c74' : FunctionalChainInvolvementLink 
                            connect source ::> 'eRod_Autonomous_Vehicle_2024 Project'::'eRod_Autonomous_Vehicle_2024'::'Logical Architecture'::'Logical Functions'::'Root Logical Function'.'Drive on Track'.'f8947e49-00c9-4657-9867-4d8132a383df'
                            to  target ::> 'eRod_Autonomous_Vehicle_2024 Project'::'eRod_Autonomous_Vehicle_2024'::'Logical Architecture'::'Logical Functions'::'Root Logical Function'.'Drive on Track'.'c73e126f-c9c6-47b9-aeb7-1db3393d5009' {

                                ref :>> involved = 'eRod_Autonomous_Vehicle_2024 Project'::'eRod_Autonomous_Vehicle_2024'::'Logical Architecture'::'Logical Functions'::'Root Logical Function'.'a4b7ed98-d219-4ab0-afad-a46848adc7ad';

                            } 
                        ref action 'c73e126f-c9c6-47b9-aeb7-1db3393d5009' = 'eRod_Autonomous_Vehicle_2024 Project'::'eRod_Autonomous_Vehicle_2024'::'Logical Architecture'::'Logical Functions'::'Root Logical Function'.'deliver mechanical power'; 
                        ref action '4cb1948e-4342-4ac3-9a23-817becd9960a' = 'eRod_Autonomous_Vehicle_2024 Project'::'eRod_Autonomous_Vehicle_2024'::'Logical Architecture'::'Logical Functions'::'Root Logical Function'.'Generate heat (Rotor)'; 
                        connection 'ce16d4da-8d27-46b9-b54a-025575fcd390' : FunctionalChainInvolvementLink 
                            connect source ::> 'eRod_Autonomous_Vehicle_2024 Project'::'eRod_Autonomous_Vehicle_2024'::'Logical Architecture'::'Logical Functions'::'Root Logical Function'.'Drive on Track'.'c73e126f-c9c6-47b9-aeb7-1db3393d5009'
                            to  target ::> 'eRod_Autonomous_Vehicle_2024 Project'::'eRod_Autonomous_Vehicle_2024'::'Logical Architecture'::'Logical Functions'::'Root Logical Function'.'Drive on Track'.'4cb1948e-4342-4ac3-9a23-817becd9960a' {

                                ref :>> involved = 'eRod_Autonomous_Vehicle_2024 Project'::'eRod_Autonomous_Vehicle_2024'::'Logical Architecture'::'Logical Functions'::'Root Logical Function'.'819c5300-ab95-4dc1-875a-b233e8abdfac';

                            } 
                        connection 'da570e23-c2ed-4b3a-933f-a69b03c03db1' : FunctionalChainInvolvementLink 
                            connect source ::> 'eRod_Autonomous_Vehicle_2024 Project'::'eRod_Autonomous_Vehicle_2024'::'Logical Architecture'::'Logical Functions'::'Root Logical Function'.'Drive on Track'.'4cb1948e-4342-4ac3-9a23-817becd9960a'
                            to  target ::> 'eRod_Autonomous_Vehicle_2024 Project'::'eRod_Autonomous_Vehicle_2024'::'Logical Architecture'::'Logical Functions'::'Root Logical Function'.'Drive on Track'.'1b4308b0-e5c2-4bc6-88b0-16d4c3869b57' {

                                ref :>> involved = 'eRod_Autonomous_Vehicle_2024 Project'::'eRod_Autonomous_Vehicle_2024'::'Logical Architecture'::'Logical Functions'::'Root Logical Function'.'fbab703c-b455-4208-af50-8fe4d4c8d693';

                            } 
                        ref action '1b4308b0-e5c2-4bc6-88b0-16d4c3869b57' = 'eRod_Autonomous_Vehicle_2024 Project'::'eRod_Autonomous_Vehicle_2024'::'Logical Architecture'::'Logical Functions'::'Root Logical Function'.'Gather 21'; 
                        connection 'e76a0141-3cb5-4449-bcfe-99afa2422aa8' : FunctionalChainInvolvementLink 
                            connect source ::> 'eRod_Autonomous_Vehicle_2024 Project'::'eRod_Autonomous_Vehicle_2024'::'Logical Architecture'::'Logical Functions'::'Root Logical Function'.'Drive on Track'.'f8947e49-00c9-4657-9867-4d8132a383df'
                            to  target ::> 'eRod_Autonomous_Vehicle_2024 Project'::'eRod_Autonomous_Vehicle_2024'::'Logical Architecture'::'Logical Functions'::'Root Logical Function'.'Drive on Track'.'9c078c34-4c78-4e10-9a43-5312173e230c' {

                                ref :>> involved = 'eRod_Autonomous_Vehicle_2024 Project'::'eRod_Autonomous_Vehicle_2024'::'Logical Architecture'::'Logical Functions'::'Root Logical Function'.'285ee071-9867-4f7f-abaf-dfbfeff65f67';

                            } 
                        ref action '9c078c34-4c78-4e10-9a43-5312173e230c' = 'eRod_Autonomous_Vehicle_2024 Project'::'eRod_Autonomous_Vehicle_2024'::'Logical Architecture'::'Logical Functions'::'Root Logical Function'.'Provide magnetic field'; 
                        connection 'c42b744e-9f6e-46f7-944c-89db3107335a' : FunctionalChainInvolvementLink 
                            connect source ::> 'eRod_Autonomous_Vehicle_2024 Project'::'eRod_Autonomous_Vehicle_2024'::'Logical Architecture'::'Logical Functions'::'Root Logical Function'.'Drive on Track'.'fd332ec1-d202-4b81-908c-fda6f4aacf08'
                            to  target ::> 'eRod_Autonomous_Vehicle_2024 Project'::'eRod_Autonomous_Vehicle_2024'::'Logical Architecture'::'Logical Functions'::'Root Logical Function'.'Drive on Track'.'1b4308b0-e5c2-4bc6-88b0-16d4c3869b57' {

                                ref :>> involved = 'eRod_Autonomous_Vehicle_2024 Project'::'eRod_Autonomous_Vehicle_2024'::'Logical Architecture'::'Logical Functions'::'Root Logical Function'.'ac15c188-c849-4add-8db5-5c783d913d61';

                            } 
                        ref action 'fd332ec1-d202-4b81-908c-fda6f4aacf08' = 'eRod_Autonomous_Vehicle_2024 Project'::'eRod_Autonomous_Vehicle_2024'::'Logical Architecture'::'Logical Functions'::'Root Logical Function'.'Generate Heat (Stator)'; 
                        connection 'f93d4c30-dc53-4ee5-a0c2-83ccd7ed99b6' : FunctionalChainInvolvementLink 
                            connect source ::> 'eRod_Autonomous_Vehicle_2024 Project'::'eRod_Autonomous_Vehicle_2024'::'Logical Architecture'::'Logical Functions'::'Root Logical Function'.'Drive on Track'.'1b4308b0-e5c2-4bc6-88b0-16d4c3869b57'
                            to  target ::> 'eRod_Autonomous_Vehicle_2024 Project'::'eRod_Autonomous_Vehicle_2024'::'Logical Architecture'::'Logical Functions'::'Root Logical Function'.'Drive on Track'.'a3e55f01-e2e2-4490-b203-401ad6fee618' {

                                ref :>> involved = 'eRod_Autonomous_Vehicle_2024 Project'::'eRod_Autonomous_Vehicle_2024'::'Logical Architecture'::'Logical Functions'::'Root Logical Function'.'3b5e8600-d938-4502-bd08-5d95e69970d5';

                            } 
                        ref action 'a3e55f01-e2e2-4490-b203-401ad6fee618' = 'eRod_Autonomous_Vehicle_2024 Project'::'eRod_Autonomous_Vehicle_2024'::'Logical Architecture'::'Logical Functions'::'Root Logical Function'.'Transfer heat'; 
                        connection 'f0f561c7-76ea-4a19-9cf0-b429057da258' : FunctionalChainInvolvementLink 
                            connect source ::> 'eRod_Autonomous_Vehicle_2024 Project'::'eRod_Autonomous_Vehicle_2024'::'Logical Architecture'::'Logical Functions'::'Root Logical Function'.'Drive on Track'.'a3e55f01-e2e2-4490-b203-401ad6fee618'
                            to  target ::> 'eRod_Autonomous_Vehicle_2024 Project'::'eRod_Autonomous_Vehicle_2024'::'Logical Architecture'::'Logical Functions'::'Root Logical Function'.'Drive on Track'.'402f9679-10cb-4b90-b017-09efe31c23fe' {

                                ref :>> involved = 'eRod_Autonomous_Vehicle_2024 Project'::'eRod_Autonomous_Vehicle_2024'::'Logical Architecture'::'Logical Functions'::'Root Logical Function'.'690b4231-60c3-43fd-ae81-d3f3f2d64519';

                            } 
                        ref action '402f9679-10cb-4b90-b017-09efe31c23fe' = 'eRod_Autonomous_Vehicle_2024 Project'::'eRod_Autonomous_Vehicle_2024'::'Logical Architecture'::'Logical Functions'::'Root Logical Function'.'Motor protect'.'Monitor temperature'; 
                        connection 'f6ac6617-f43b-4c9a-ba56-732db78a1c25' : FunctionalChainInvolvementLink 
                            connect source ::> 'eRod_Autonomous_Vehicle_2024 Project'::'eRod_Autonomous_Vehicle_2024'::'Logical Architecture'::'Logical Functions'::'Root Logical Function'.'Drive on Track'.'402f9679-10cb-4b90-b017-09efe31c23fe'
                            to  target ::> 'eRod_Autonomous_Vehicle_2024 Project'::'eRod_Autonomous_Vehicle_2024'::'Logical Architecture'::'Logical Functions'::'Root Logical Function'.'Drive on Track'.'bfda3a5d-d1ca-4f77-b69c-d34fbc226ca9' {

                                ref :>> involved = 'eRod_Autonomous_Vehicle_2024 Project'::'eRod_Autonomous_Vehicle_2024'::'Logical Architecture'::'Logical Functions'::'Root Logical Function'.'Motor protect'.'ef57735d-e98b-466c-be56-d8fbca4ab801';

                            } 
                        ref action 'bfda3a5d-d1ca-4f77-b69c-d34fbc226ca9' = 'eRod_Autonomous_Vehicle_2024 Project'::'eRod_Autonomous_Vehicle_2024'::'Logical Architecture'::'Logical Functions'::'Root Logical Function'.'Motor protect'.'Detect temperature limit'; 
                        connection 'b9546506-f433-4f3f-b987-e584b1058a34' : FunctionalChainInvolvementLink 
                            connect source ::> 'eRod_Autonomous_Vehicle_2024 Project'::'eRod_Autonomous_Vehicle_2024'::'Logical Architecture'::'Logical Functions'::'Root Logical Function'.'Drive on Track'.'bfda3a5d-d1ca-4f77-b69c-d34fbc226ca9'
                            to  target ::> 'eRod_Autonomous_Vehicle_2024 Project'::'eRod_Autonomous_Vehicle_2024'::'Logical Architecture'::'Logical Functions'::'Root Logical Function'.'Drive on Track'.'6114d46d-a281-43b5-94c6-b4778d04e53d' {

                                ref :>> involved = 'eRod_Autonomous_Vehicle_2024 Project'::'eRod_Autonomous_Vehicle_2024'::'Logical Architecture'::'Logical Functions'::'Root Logical Function'.'76b26dd2-2a46-4b84-b303-1c3132586ce4';

                            } 
                        ref action '6114d46d-a281-43b5-94c6-b4778d04e53d' = 'eRod_Autonomous_Vehicle_2024 Project'::'eRod_Autonomous_Vehicle_2024'::'Logical Architecture'::'Logical Functions'::'Root Logical Function'.'Motor overheating warning '; 
                         
                    }  
                    action 'Detect Temp Issues' : FunctionalChain  { 
                        @CapellaID { eid = "942cd2aa-4158-4e3b-a97b-903f5023d8c2"; } 
                        attribute :>> kind = FunctionalChainKind::SIMPLE; 
                        ref action '7ff7b346-b5c5-465e-bab2-3ab597802c33' = 'eRod_Autonomous_Vehicle_2024 Project'::'eRod_Autonomous_Vehicle_2024'::'Logical Architecture'::'Logical Functions'::'Root Logical Function'.'Motor protect'.'Detect temperature limit'; 
                        connection '960d5243-b950-4129-8f59-7076e41a4257' : FunctionalChainInvolvementLink 
                            connect source ::> 'eRod_Autonomous_Vehicle_2024 Project'::'eRod_Autonomous_Vehicle_2024'::'Logical Architecture'::'Logical Functions'::'Root Logical Function'.'Detect Temp Issues'.'7ff7b346-b5c5-465e-bab2-3ab597802c33'
                            to  target ::> 'eRod_Autonomous_Vehicle_2024 Project'::'eRod_Autonomous_Vehicle_2024'::'Logical Architecture'::'Logical Functions'::'Root Logical Function'.'Detect Temp Issues'.'a49cb76d-1869-462a-a0d1-12ef808f3793' {

                                ref :>> involved = 'eRod_Autonomous_Vehicle_2024 Project'::'eRod_Autonomous_Vehicle_2024'::'Logical Architecture'::'Logical Functions'::'Root Logical Function'.'Motor protect'.'57378bfd-1c57-40f3-a130-a89cc2cc13d8';

                            } 
                        ref action 'a49cb76d-1869-462a-a0d1-12ef808f3793' = 'eRod_Autonomous_Vehicle_2024 Project'::'eRod_Autonomous_Vehicle_2024'::'Logical Architecture'::'Logical Functions'::'Root Logical Function'.'Motor protect'.'Reduce power'; 
                        connection '77f53eb9-606a-4eee-9fd6-596d5835e4bb' : FunctionalChainInvolvementLink 
                            connect source ::> 'eRod_Autonomous_Vehicle_2024 Project'::'eRod_Autonomous_Vehicle_2024'::'Logical Architecture'::'Logical Functions'::'Root Logical Function'.'Detect Temp Issues'.'a49cb76d-1869-462a-a0d1-12ef808f3793'
                            to  target ::> 'eRod_Autonomous_Vehicle_2024 Project'::'eRod_Autonomous_Vehicle_2024'::'Logical Architecture'::'Logical Functions'::'Root Logical Function'.'Detect Temp Issues'.'9ffe6179-bd39-4ce6-b785-624c87ef2a44' {

                                ref :>> involved = 'eRod_Autonomous_Vehicle_2024 Project'::'eRod_Autonomous_Vehicle_2024'::'Logical Architecture'::'Logical Functions'::'Root Logical Function'.'9834ba0a-fa40-4c5c-b41c-f4eab563640f';

                            } 
                        ref action '9ffe6179-bd39-4ce6-b785-624c87ef2a44' = 'eRod_Autonomous_Vehicle_2024 Project'::'eRod_Autonomous_Vehicle_2024'::'Logical Architecture'::'Logical Functions'::'Root Logical Function'.'deliver mechanical power'; 
                        connection 'ab629790-38b6-48cc-a469-f26b31c65a3d' : FunctionalChainInvolvementLink 
                            connect source ::> 'eRod_Autonomous_Vehicle_2024 Project'::'eRod_Autonomous_Vehicle_2024'::'Logical Architecture'::'Logical Functions'::'Root Logical Function'.'Detect Temp Issues'.'9ffe6179-bd39-4ce6-b785-624c87ef2a44'
                            to  target ::> 'eRod_Autonomous_Vehicle_2024 Project'::'eRod_Autonomous_Vehicle_2024'::'Logical Architecture'::'Logical Functions'::'Root Logical Function'.'Detect Temp Issues'.'16c25d4c-2b8f-4419-b928-373574578f0d' {

                                ref :>> involved = 'eRod_Autonomous_Vehicle_2024 Project'::'eRod_Autonomous_Vehicle_2024'::'Logical Architecture'::'Logical Functions'::'Root Logical Function'.'1cbd00ec-4044-4944-96b5-97902f698ad7';

                            } 
                        ref action '16c25d4c-2b8f-4419-b928-373574578f0d' = 'eRod_Autonomous_Vehicle_2024 Project'::'eRod_Autonomous_Vehicle_2024'::'Logical Architecture'::'Logical Functions'::'Root Logical Function'.'Transfer power to Axies'; 
                        connection '3de895f0-6b03-4913-af40-f04de8b86d60' : FunctionalChainInvolvementLink 
                            connect source ::> 'eRod_Autonomous_Vehicle_2024 Project'::'eRod_Autonomous_Vehicle_2024'::'Logical Architecture'::'Logical Functions'::'Root Logical Function'.'Detect Temp Issues'.'16c25d4c-2b8f-4419-b928-373574578f0d'
                            to  target ::> 'eRod_Autonomous_Vehicle_2024 Project'::'eRod_Autonomous_Vehicle_2024'::'Logical Architecture'::'Logical Functions'::'Root Logical Function'.'Detect Temp Issues'.'11faf983-4c19-41b0-826f-9746684ee27e' {

                                ref :>> involved = 'eRod_Autonomous_Vehicle_2024 Project'::'eRod_Autonomous_Vehicle_2024'::'Logical Architecture'::'Logical Functions'::'Root Logical Function'.'ad75ca27-9657-4f7a-b9f0-91f8f72375b0';

                            } 
                        ref action '11faf983-4c19-41b0-826f-9746684ee27e' = 'eRod_Autonomous_Vehicle_2024 Project'::'eRod_Autonomous_Vehicle_2024'::'Logical Architecture'::'Logical Functions'::'Root Logical Function'.'Apply rotation on wheels'; 
                        connection 'fc0196ca-83c4-4812-ab15-387bdbd731f9' : FunctionalChainInvolvementLink 
                            connect source ::> 'eRod_Autonomous_Vehicle_2024 Project'::'eRod_Autonomous_Vehicle_2024'::'Logical Architecture'::'Logical Functions'::'Root Logical Function'.'Detect Temp Issues'.'11faf983-4c19-41b0-826f-9746684ee27e'
                            to  target ::> 'eRod_Autonomous_Vehicle_2024 Project'::'eRod_Autonomous_Vehicle_2024'::'Logical Architecture'::'Logical Functions'::'Root Logical Function'.'Detect Temp Issues'.'43287f12-46ae-4d7b-a8a0-4ff410baed1a' {

                                ref :>> involved = 'eRod_Autonomous_Vehicle_2024 Project'::'eRod_Autonomous_Vehicle_2024'::'Logical Architecture'::'Logical Functions'::'Root Logical Function'.'ffd7802c-2093-4298-a18f-a98778d74812';

                            } 
                        ref action '43287f12-46ae-4d7b-a8a0-4ff410baed1a' = 'eRod_Autonomous_Vehicle_2024 Project'::'eRod_Autonomous_Vehicle_2024'::'Logical Architecture'::'Logical Functions'::'Root Logical Function'.'Split 25'; 
                        connection 'd0e47b0e-cade-43b1-963c-ffedc4c7b81f' : FunctionalChainInvolvementLink 
                            connect source ::> 'eRod_Autonomous_Vehicle_2024 Project'::'eRod_Autonomous_Vehicle_2024'::'Logical Architecture'::'Logical Functions'::'Root Logical Function'.'Detect Temp Issues'.'43287f12-46ae-4d7b-a8a0-4ff410baed1a'
                            to  target ::> 'eRod_Autonomous_Vehicle_2024 Project'::'eRod_Autonomous_Vehicle_2024'::'Logical Architecture'::'Logical Functions'::'Root Logical Function'.'Detect Temp Issues'.'ef1b18d8-5869-4381-8922-6d7f0e37c776' {

                                ref :>> involved = 'eRod_Autonomous_Vehicle_2024 Project'::'eRod_Autonomous_Vehicle_2024'::'Logical Architecture'::'Logical Functions'::'Root Logical Function'.'19d12ee0-70a6-49d7-9468-396730331e38';

                            } 
                        ref action 'ef1b18d8-5869-4381-8922-6d7f0e37c776' = 'eRod_Autonomous_Vehicle_2024 Project'::'eRod_Autonomous_Vehicle_2024'::'Logical Architecture'::'Logical Functions'::'Root Logical Function'.'Deaccelerate'; 
                        connection '4033ef90-91b7-4a88-b767-4a1b5eec2d38' : FunctionalChainInvolvementLink 
                            connect source ::> 'eRod_Autonomous_Vehicle_2024 Project'::'eRod_Autonomous_Vehicle_2024'::'Logical Architecture'::'Logical Functions'::'Root Logical Function'.'Detect Temp Issues'.'ef1b18d8-5869-4381-8922-6d7f0e37c776'
                            to  target ::> 'eRod_Autonomous_Vehicle_2024 Project'::'eRod_Autonomous_Vehicle_2024'::'Logical Architecture'::'Logical Functions'::'Root Logical Function'.'Detect Temp Issues'.'b6a73d16-44b4-4cdd-b060-e6ea190108ac' {

                                ref :>> involved = 'eRod_Autonomous_Vehicle_2024 Project'::'eRod_Autonomous_Vehicle_2024'::'Logical Architecture'::'Logical Functions'::'Root Logical Function'.'89d97516-8ef5-40a7-98d5-18282eaded97';

                            } 
                        ref action 'b6a73d16-44b4-4cdd-b060-e6ea190108ac' = 'eRod_Autonomous_Vehicle_2024 Project'::'eRod_Autonomous_Vehicle_2024'::'Logical Architecture'::'Logical Functions'::'Root Logical Function'.'Stop'; 
                        connection '6b4c405d-800a-4543-ae29-ef7e007f801e' : FunctionalChainInvolvementLink 
                            connect source ::> 'eRod_Autonomous_Vehicle_2024 Project'::'eRod_Autonomous_Vehicle_2024'::'Logical Architecture'::'Logical Functions'::'Root Logical Function'.'Detect Temp Issues'.'b6a73d16-44b4-4cdd-b060-e6ea190108ac'
                            to  target ::> 'eRod_Autonomous_Vehicle_2024 Project'::'eRod_Autonomous_Vehicle_2024'::'Logical Architecture'::'Logical Functions'::'Root Logical Function'.'Detect Temp Issues'.'4f4a2cc5-2713-4582-a7a2-53c4415db65a' {

                                ref :>> involved = 'eRod_Autonomous_Vehicle_2024 Project'::'eRod_Autonomous_Vehicle_2024'::'Logical Architecture'::'Logical Functions'::'Root Logical Function'.'b953457a-88f3-40b9-a380-8bbaeb6110c8';

                            } 
                        ref action '4f4a2cc5-2713-4582-a7a2-53c4415db65a' = 'eRod_Autonomous_Vehicle_2024 Project'::'eRod_Autonomous_Vehicle_2024'::'Logical Architecture'::'Logical Functions'::'Root Logical Function'.'Car racing experience absorbed'; 
                         
                    }  
                    action 'Software update' : FunctionalChain  { 
                        @CapellaID { eid = "2a952732-3189-4654-81ac-62907da64aa4"; } 
                        attribute :>> kind = FunctionalChainKind::SIMPLE; 
                        ref action '6bee5792-3cc7-4f2e-b8f1-e286caa622e6' = 'eRod_Autonomous_Vehicle_2024 Project'::'eRod_Autonomous_Vehicle_2024'::'Logical Architecture'::'Logical Functions'::'Root Logical Function'.'Improve motor performance'; 
                        ref action '062200df-fc41-47ae-aa43-80649e306a03' = 'eRod_Autonomous_Vehicle_2024 Project'::'eRod_Autonomous_Vehicle_2024'::'Logical Architecture'::'Logical Functions'::'Root Logical Function'.'Sporty drive'; 
                        connection 'df9b2fb5-b1f0-490a-b05c-39d03302a25c' : FunctionalChainInvolvementLink 
                            connect source ::> 'eRod_Autonomous_Vehicle_2024 Project'::'eRod_Autonomous_Vehicle_2024'::'Logical Architecture'::'Logical Functions'::'Root Logical Function'.'Software update'.'062200df-fc41-47ae-aa43-80649e306a03'
                            to  target ::> 'eRod_Autonomous_Vehicle_2024 Project'::'eRod_Autonomous_Vehicle_2024'::'Logical Architecture'::'Logical Functions'::'Root Logical Function'.'Software update'.'ea873869-f8fe-4f54-b0c0-174501edb1fb' {

                                ref :>> involved = 'eRod_Autonomous_Vehicle_2024 Project'::'eRod_Autonomous_Vehicle_2024'::'Logical Architecture'::'Logical Functions'::'Root Logical Function'.'e8eeb1b5-4b14-436d-939f-422741f61b33';

                            } 
                        ref action 'ea873869-f8fe-4f54-b0c0-174501edb1fb' = 'eRod_Autonomous_Vehicle_2024 Project'::'eRod_Autonomous_Vehicle_2024'::'Logical Architecture'::'Logical Functions'::'Root Logical Function'.'Obtain car racing experience'; 
                        ref action 'b3c9268e-3725-4efd-8b87-83cf9c1786c8' = 'eRod_Autonomous_Vehicle_2024 Project'::'eRod_Autonomous_Vehicle_2024'::'Logical Architecture'::'Logical Functions'::'Root Logical Function'.'Recieve feedback'; 
                        connection '7c6862be-dfe4-4818-9b02-3e6ffcefd6f5' : FunctionalChainInvolvementLink 
                            connect source ::> 'eRod_Autonomous_Vehicle_2024 Project'::'eRod_Autonomous_Vehicle_2024'::'Logical Architecture'::'Logical Functions'::'Root Logical Function'.'Software update'.'b3c9268e-3725-4efd-8b87-83cf9c1786c8'
                            to  target ::> 'eRod_Autonomous_Vehicle_2024 Project'::'eRod_Autonomous_Vehicle_2024'::'Logical Architecture'::'Logical Functions'::'Root Logical Function'.'Software update'.'3d5fca81-0e0b-452b-a85c-a0c7debbf0be' {

                                ref :>> involved = 'eRod_Autonomous_Vehicle_2024 Project'::'eRod_Autonomous_Vehicle_2024'::'Logical Architecture'::'Logical Functions'::'Root Logical Function'.'edd168dc-8fa2-4b10-a831-c8e652921b81';

                            } 
                        ref action '3d5fca81-0e0b-452b-a85c-a0c7debbf0be' = 'eRod_Autonomous_Vehicle_2024 Project'::'eRod_Autonomous_Vehicle_2024'::'Logical Architecture'::'Logical Functions'::'Root Logical Function'.'Provide solution'; 
                        connection '03950c74-28b9-404b-bcb1-2e6fa1225a15' : FunctionalChainInvolvementLink 
                            connect source ::> 'eRod_Autonomous_Vehicle_2024 Project'::'eRod_Autonomous_Vehicle_2024'::'Logical Architecture'::'Logical Functions'::'Root Logical Function'.'Software update'.'3d5fca81-0e0b-452b-a85c-a0c7debbf0be'
                            to  target ::> 'eRod_Autonomous_Vehicle_2024 Project'::'eRod_Autonomous_Vehicle_2024'::'Logical Architecture'::'Logical Functions'::'Root Logical Function'.'Software update'.'b00c7f11-c161-42ff-8be3-dbf52e493e47' {

                                ref :>> involved = 'eRod_Autonomous_Vehicle_2024 Project'::'eRod_Autonomous_Vehicle_2024'::'Logical Architecture'::'Logical Functions'::'Root Logical Function'.'a57e94d5-e777-4b4c-aa5f-ac2d8595ac03';

                            } 
                        ref action 'b00c7f11-c161-42ff-8be3-dbf52e493e47' = 'eRod_Autonomous_Vehicle_2024 Project'::'eRod_Autonomous_Vehicle_2024'::'Logical Architecture'::'Logical Functions'::'Root Logical Function'.'Get Software-update'; 
                        connection 'e0ab3f1d-e181-483a-9cae-bbbbf095c268' : FunctionalChainInvolvementLink 
                            connect source ::> 'eRod_Autonomous_Vehicle_2024 Project'::'eRod_Autonomous_Vehicle_2024'::'Logical Architecture'::'Logical Functions'::'Root Logical Function'.'Software update'.'b00c7f11-c161-42ff-8be3-dbf52e493e47'
                            to  target ::> 'eRod_Autonomous_Vehicle_2024 Project'::'eRod_Autonomous_Vehicle_2024'::'Logical Architecture'::'Logical Functions'::'Root Logical Function'.'Software update'.'34347464-c2a6-4a2a-a7a3-441fd7e788a2' {

                                ref :>> involved = 'eRod_Autonomous_Vehicle_2024 Project'::'eRod_Autonomous_Vehicle_2024'::'Logical Architecture'::'Logical Functions'::'Root Logical Function'.'4de49d8e-32ac-4c58-804a-16d3f40ee573';

                            } 
                        ref action '34347464-c2a6-4a2a-a7a3-441fd7e788a2' = 'eRod_Autonomous_Vehicle_2024 Project'::'eRod_Autonomous_Vehicle_2024'::'Logical Architecture'::'Logical Functions'::'Root Logical Function'.'connected to the center'; 
                        connection '0c2e074f-d26c-441e-b628-eadf824db759' : FunctionalChainInvolvementLink 
                            connect source ::> 'eRod_Autonomous_Vehicle_2024 Project'::'eRod_Autonomous_Vehicle_2024'::'Logical Architecture'::'Logical Functions'::'Root Logical Function'.'Software update'.'b00c7f11-c161-42ff-8be3-dbf52e493e47'
                            to  target ::> 'eRod_Autonomous_Vehicle_2024 Project'::'eRod_Autonomous_Vehicle_2024'::'Logical Architecture'::'Logical Functions'::'Root Logical Function'.'Software update'.'6bee5792-3cc7-4f2e-b8f1-e286caa622e6' {

                                ref :>> involved = 'eRod_Autonomous_Vehicle_2024 Project'::'eRod_Autonomous_Vehicle_2024'::'Logical Architecture'::'Logical Functions'::'Root Logical Function'.'cccc8414-558e-44b8-b776-c579e6e76e24';

                            } 
                        connection 'e26e43d1-6f0d-47c0-a86b-ca8fbff83365' : FunctionalChainInvolvementLink 
                            connect source ::> 'eRod_Autonomous_Vehicle_2024 Project'::'eRod_Autonomous_Vehicle_2024'::'Logical Architecture'::'Logical Functions'::'Root Logical Function'.'Software update'.'b00c7f11-c161-42ff-8be3-dbf52e493e47'
                            to  target ::> 'eRod_Autonomous_Vehicle_2024 Project'::'eRod_Autonomous_Vehicle_2024'::'Logical Architecture'::'Logical Functions'::'Root Logical Function'.'Software update'.'ea873869-f8fe-4f54-b0c0-174501edb1fb' {

                                ref :>> involved = 'eRod_Autonomous_Vehicle_2024 Project'::'eRod_Autonomous_Vehicle_2024'::'Logical Architecture'::'Logical Functions'::'Root Logical Function'.'f556bb6e-428a-4906-ba9f-e0b9b35648e1';

                            } 
                        ref action '724e6ac0-0d86-4b7b-9c68-9f3d6fcc890e' = 'eRod_Autonomous_Vehicle_2024 Project'::'eRod_Autonomous_Vehicle_2024'::'Logical Architecture'::'Logical Functions'::'Root Logical Function'.'Report issues'; 
                        connection '4042ce1c-9afc-4ab8-9c26-962fff39007c' : FunctionalChainInvolvementLink 
                            connect source ::> 'eRod_Autonomous_Vehicle_2024 Project'::'eRod_Autonomous_Vehicle_2024'::'Logical Architecture'::'Logical Functions'::'Root Logical Function'.'Software update'.'724e6ac0-0d86-4b7b-9c68-9f3d6fcc890e'
                            to  target ::> 'eRod_Autonomous_Vehicle_2024 Project'::'eRod_Autonomous_Vehicle_2024'::'Logical Architecture'::'Logical Functions'::'Root Logical Function'.'Software update'.'b3c9268e-3725-4efd-8b87-83cf9c1786c8' {

                                ref :>> involved = 'eRod_Autonomous_Vehicle_2024 Project'::'eRod_Autonomous_Vehicle_2024'::'Logical Architecture'::'Logical Functions'::'Root Logical Function'.'033494da-7516-44f8-a2d3-007f5e9f12cd';

                            } 
                        ref action 'dfe7db88-0c50-4d0f-87cb-4a2c54f0d4cb' = 'eRod_Autonomous_Vehicle_2024 Project'::'eRod_Autonomous_Vehicle_2024'::'Logical Architecture'::'Logical Functions'::'Root Logical Function'.'Get informed with issues'; 
                        connection '691e8556-c97b-4724-8b0f-f44e86c7e8b0' : FunctionalChainInvolvementLink 
                            connect source ::> 'eRod_Autonomous_Vehicle_2024 Project'::'eRod_Autonomous_Vehicle_2024'::'Logical Architecture'::'Logical Functions'::'Root Logical Function'.'Software update'.'dfe7db88-0c50-4d0f-87cb-4a2c54f0d4cb'
                            to  target ::> 'eRod_Autonomous_Vehicle_2024 Project'::'eRod_Autonomous_Vehicle_2024'::'Logical Architecture'::'Logical Functions'::'Root Logical Function'.'Software update'.'724e6ac0-0d86-4b7b-9c68-9f3d6fcc890e' {

                                ref :>> involved = 'eRod_Autonomous_Vehicle_2024 Project'::'eRod_Autonomous_Vehicle_2024'::'Logical Architecture'::'Logical Functions'::'Root Logical Function'.'0e825f29-7978-4cea-92bf-ed5a75495285';

                            } 
                        ref action '88dd2c09-0427-4b26-b7d2-b014d34927e8' = 'eRod_Autonomous_Vehicle_2024 Project'::'eRod_Autonomous_Vehicle_2024'::'Logical Architecture'::'Logical Functions'::'Root Logical Function'.'Motor overheating warning '; 
                        connection '8bc2341c-7955-4b06-9b94-b70a5599e4dc' : FunctionalChainInvolvementLink 
                            connect source ::> 'eRod_Autonomous_Vehicle_2024 Project'::'eRod_Autonomous_Vehicle_2024'::'Logical Architecture'::'Logical Functions'::'Root Logical Function'.'Software update'.'88dd2c09-0427-4b26-b7d2-b014d34927e8'
                            to  target ::> 'eRod_Autonomous_Vehicle_2024 Project'::'eRod_Autonomous_Vehicle_2024'::'Logical Architecture'::'Logical Functions'::'Root Logical Function'.'Software update'.'dfe7db88-0c50-4d0f-87cb-4a2c54f0d4cb' {

                                ref :>> involved = 'eRod_Autonomous_Vehicle_2024 Project'::'eRod_Autonomous_Vehicle_2024'::'Logical Architecture'::'Logical Functions'::'Root Logical Function'.'49b41474-6068-48af-9f20-48587c061248';

                            } 
                         
                    }  
                    action 'Automatic Emergency Braking (AEB)' : FunctionalChain  { 
                        @CapellaID { eid = "05692c3e-dc6c-4e68-9369-922ad5fbbb91"; } 
                        attribute :>> kind = FunctionalChainKind::SIMPLE; 
                        connection '9a1de089-0de9-47da-bb8b-06131ae83401' : FunctionalChainInvolvementLink 
                            connect source ::> 'eRod_Autonomous_Vehicle_2024 Project'::'eRod_Autonomous_Vehicle_2024'::'Logical Architecture'::'Logical Functions'::'Root Logical Function'.'Automatic Emergency Braking (AEB)'.'a46ba8d1-4e7d-4870-ac5a-9223558138a1'
                            to  target ::> 'eRod_Autonomous_Vehicle_2024 Project'::'eRod_Autonomous_Vehicle_2024'::'Logical Architecture'::'Logical Functions'::'Root Logical Function'.'Automatic Emergency Braking (AEB)'.'e5a87a2d-5cfc-41af-afb7-a63dc5459e8c' {

                                ref :>> involved = 'eRod_Autonomous_Vehicle_2024 Project'::'eRod_Autonomous_Vehicle_2024'::'Logical Architecture'::'Logical Functions'::'Root Logical Function'.'87b8ca06-8640-467a-acf3-2885332412f6';

                            } 
                        ref action 'e5a87a2d-5cfc-41af-afb7-a63dc5459e8c' = 'eRod_Autonomous_Vehicle_2024 Project'::'eRod_Autonomous_Vehicle_2024'::'Logical Architecture'::'Logical Functions'::'Root Logical Function'.'Locate targets'; 
                        ref action 'a46ba8d1-4e7d-4870-ac5a-9223558138a1' = 'eRod_Autonomous_Vehicle_2024 Project'::'eRod_Autonomous_Vehicle_2024'::'Logical Architecture'::'Logical Functions'::'Root Logical Function'.'Provide object location'; 
                        connection 'ca728494-7681-4805-ade5-74f95978c165' : FunctionalChainInvolvementLink 
                            connect source ::> 'eRod_Autonomous_Vehicle_2024 Project'::'eRod_Autonomous_Vehicle_2024'::'Logical Architecture'::'Logical Functions'::'Root Logical Function'.'Automatic Emergency Braking (AEB)'.'e5a87a2d-5cfc-41af-afb7-a63dc5459e8c'
                            to  target ::> 'eRod_Autonomous_Vehicle_2024 Project'::'eRod_Autonomous_Vehicle_2024'::'Logical Architecture'::'Logical Functions'::'Root Logical Function'.'Automatic Emergency Braking (AEB)'.'bbc4ba28-2259-4ecc-b30a-9e4b92172997' {

                                ref :>> involved = 'eRod_Autonomous_Vehicle_2024 Project'::'eRod_Autonomous_Vehicle_2024'::'Logical Architecture'::'Logical Functions'::'Root Logical Function'.'d18a222b-3410-46f6-a2c5-3b0367587d3a';

                            } 
                        ref action 'bbc4ba28-2259-4ecc-b30a-9e4b92172997' = 'eRod_Autonomous_Vehicle_2024 Project'::'eRod_Autonomous_Vehicle_2024'::'Logical Architecture'::'Logical Functions'::'Root Logical Function'.'Avoid collision'; 
                        connection 'e0df4807-f24b-4f4b-b999-a29d9c07942c' : FunctionalChainInvolvementLink 
                            connect source ::> 'eRod_Autonomous_Vehicle_2024 Project'::'eRod_Autonomous_Vehicle_2024'::'Logical Architecture'::'Logical Functions'::'Root Logical Function'.'Automatic Emergency Braking (AEB)'.'bbc4ba28-2259-4ecc-b30a-9e4b92172997'
                            to  target ::> 'eRod_Autonomous_Vehicle_2024 Project'::'eRod_Autonomous_Vehicle_2024'::'Logical Architecture'::'Logical Functions'::'Root Logical Function'.'Automatic Emergency Braking (AEB)'.'23920e3a-0f5c-4a60-835e-88bd2d2160c3' {

                                ref :>> involved = 'eRod_Autonomous_Vehicle_2024 Project'::'eRod_Autonomous_Vehicle_2024'::'Logical Architecture'::'Logical Functions'::'Root Logical Function'.'a5ebfdbf-73c1-4d59-862b-88888f9d7104';

                            } 
                        ref action '23920e3a-0f5c-4a60-835e-88bd2d2160c3' = 'eRod_Autonomous_Vehicle_2024 Project'::'eRod_Autonomous_Vehicle_2024'::'Logical Architecture'::'Logical Functions'::'Root Logical Function'.'Slow down and stop the vehicle'; 
                         
                    }  
                    action 'Forward Collision Warning (FCW)' : FunctionalChain  { 
                        @CapellaID { eid = "fc83b369-c392-422d-a0c1-4eed680d00d0"; } 
                        attribute :>> kind = FunctionalChainKind::SIMPLE; 
                        connection '0dcd3699-a7b5-4db7-9289-08cb896e8169' : FunctionalChainInvolvementLink 
                            connect source ::> 'eRod_Autonomous_Vehicle_2024 Project'::'eRod_Autonomous_Vehicle_2024'::'Logical Architecture'::'Logical Functions'::'Root Logical Function'.'Forward Collision Warning (FCW)'.'3f9ca716-23ed-4908-9266-7d201be2a8ba'
                            to  target ::> 'eRod_Autonomous_Vehicle_2024 Project'::'eRod_Autonomous_Vehicle_2024'::'Logical Architecture'::'Logical Functions'::'Root Logical Function'.'Forward Collision Warning (FCW)'.'f76bf34a-76e5-4c42-8185-aaad4258259b' {

                                ref :>> involved = 'eRod_Autonomous_Vehicle_2024 Project'::'eRod_Autonomous_Vehicle_2024'::'Logical Architecture'::'Logical Functions'::'Root Logical Function'.'5684217c-ef08-4a13-a10f-2be25d9ef9bf';

                            } 
                        ref action 'f76bf34a-76e5-4c42-8185-aaad4258259b' = 'eRod_Autonomous_Vehicle_2024 Project'::'eRod_Autonomous_Vehicle_2024'::'Logical Architecture'::'Logical Functions'::'Root Logical Function'.'Provide vehicle status'; 
                        ref action '3f9ca716-23ed-4908-9266-7d201be2a8ba' = 'eRod_Autonomous_Vehicle_2024 Project'::'eRod_Autonomous_Vehicle_2024'::'Logical Architecture'::'Logical Functions'::'Root Logical Function'.'Avoid collision'; 
                        connection 'bd132365-5df5-455f-a6dd-c75a1f001a3c' : FunctionalChainInvolvementLink 
                            connect source ::> 'eRod_Autonomous_Vehicle_2024 Project'::'eRod_Autonomous_Vehicle_2024'::'Logical Architecture'::'Logical Functions'::'Root Logical Function'.'Forward Collision Warning (FCW)'.'f76bf34a-76e5-4c42-8185-aaad4258259b'
                            to  target ::> 'eRod_Autonomous_Vehicle_2024 Project'::'eRod_Autonomous_Vehicle_2024'::'Logical Architecture'::'Logical Functions'::'Root Logical Function'.'Forward Collision Warning (FCW)'.'9709f66e-da4d-4ca0-8d4b-f1a32ce279df' {

                                ref :>> involved = 'eRod_Autonomous_Vehicle_2024 Project'::'eRod_Autonomous_Vehicle_2024'::'Logical Architecture'::'Logical Functions'::'Root Logical Function'.'e8a1b447-aae8-462f-83d2-e68efe8d3ed1';

                            } 
                        ref action '9709f66e-da4d-4ca0-8d4b-f1a32ce279df' = 'eRod_Autonomous_Vehicle_2024 Project'::'eRod_Autonomous_Vehicle_2024'::'Logical Architecture'::'Logical Functions'::'Root Logical Function'.'Observe status'; 
                         
                    }  
                    action 'Adaptive Cruise Control (ACC)' : FunctionalChain  { 
                        @CapellaID { eid = "a0df9eb5-b379-4f4f-ad61-d0b8146f0ff4"; } 
                        attribute :>> kind = FunctionalChainKind::SIMPLE; 
                        connection '2f8bc8bf-2805-47db-a61c-3f8c5aecdc9c' : FunctionalChainInvolvementLink 
                            connect source ::> 'eRod_Autonomous_Vehicle_2024 Project'::'eRod_Autonomous_Vehicle_2024'::'Logical Architecture'::'Logical Functions'::'Root Logical Function'.'Adaptive Cruise Control (ACC)'.'2fb5cd2b-3fec-4509-b6e6-9c7d2b431853'
                            to  target ::> 'eRod_Autonomous_Vehicle_2024 Project'::'eRod_Autonomous_Vehicle_2024'::'Logical Architecture'::'Logical Functions'::'Root Logical Function'.'Adaptive Cruise Control (ACC)'.'86ac96c4-01d1-4741-89e9-64d1c3fb4e01' {

                                ref :>> involved = 'eRod_Autonomous_Vehicle_2024 Project'::'eRod_Autonomous_Vehicle_2024'::'Logical Architecture'::'Logical Functions'::'Root Logical Function'.'94b73d74-b009-4feb-8fe1-ab408ade5c40';

                            } 
                        ref action '86ac96c4-01d1-4741-89e9-64d1c3fb4e01' = 'eRod_Autonomous_Vehicle_2024 Project'::'eRod_Autonomous_Vehicle_2024'::'Logical Architecture'::'Logical Functions'::'Root Logical Function'.'Maintain distance'; 
                        ref action '2fb5cd2b-3fec-4509-b6e6-9c7d2b431853' = 'eRod_Autonomous_Vehicle_2024 Project'::'eRod_Autonomous_Vehicle_2024'::'Logical Architecture'::'Logical Functions'::'Root Logical Function'.'Locate targets'; 
                        connection '3248a211-d2d9-4f18-9d0b-d26b1572b112' : FunctionalChainInvolvementLink 
                            connect source ::> 'eRod_Autonomous_Vehicle_2024 Project'::'eRod_Autonomous_Vehicle_2024'::'Logical Architecture'::'Logical Functions'::'Root Logical Function'.'Adaptive Cruise Control (ACC)'.'86ac96c4-01d1-4741-89e9-64d1c3fb4e01'
                            to  target ::> 'eRod_Autonomous_Vehicle_2024 Project'::'eRod_Autonomous_Vehicle_2024'::'Logical Architecture'::'Logical Functions'::'Root Logical Function'.'Adaptive Cruise Control (ACC)'.'598e363e-6019-40f4-9bb9-6a2b89b60ea7' {

                                ref :>> involved = 'eRod_Autonomous_Vehicle_2024 Project'::'eRod_Autonomous_Vehicle_2024'::'Logical Architecture'::'Logical Functions'::'Root Logical Function'.'9f372622-48b8-4830-944f-8ee72350a823';

                            } 
                        ref action '598e363e-6019-40f4-9bb9-6a2b89b60ea7' = 'eRod_Autonomous_Vehicle_2024 Project'::'eRod_Autonomous_Vehicle_2024'::'Logical Architecture'::'Logical Functions'::'Root Logical Function'.'Slow down and stop the vehicle'; 
                        ref action 'aed8f724-2b41-4895-890f-31d69e2fe3be' = 'eRod_Autonomous_Vehicle_2024 Project'::'eRod_Autonomous_Vehicle_2024'::'Logical Architecture'::'Logical Functions'::'Root Logical Function'.'Maintain speed'; 
                        connection '2b13a62a-94ce-4ddd-9d09-d18e32bde865' : FunctionalChainInvolvementLink 
                            connect source ::> 'eRod_Autonomous_Vehicle_2024 Project'::'eRod_Autonomous_Vehicle_2024'::'Logical Architecture'::'Logical Functions'::'Root Logical Function'.'Adaptive Cruise Control (ACC)'.'86ac96c4-01d1-4741-89e9-64d1c3fb4e01'
                            to  target ::> 'eRod_Autonomous_Vehicle_2024 Project'::'eRod_Autonomous_Vehicle_2024'::'Logical Architecture'::'Logical Functions'::'Root Logical Function'.'Adaptive Cruise Control (ACC)'.'aed8f724-2b41-4895-890f-31d69e2fe3be' {

                                ref :>> involved = 'eRod_Autonomous_Vehicle_2024 Project'::'eRod_Autonomous_Vehicle_2024'::'Logical Architecture'::'Logical Functions'::'Root Logical Function'.'a59d2706-68ee-49d5-9dcc-1fe46eaaac5d';

                            } 
                        ref action '63c4b16b-8f2e-4cc8-8219-82b4992a9585' = 'eRod_Autonomous_Vehicle_2024 Project'::'eRod_Autonomous_Vehicle_2024'::'Logical Architecture'::'Logical Functions'::'Root Logical Function'.'Provide target vehicle velocity'; 
                        connection '812a4f8f-2d65-459d-a0a5-5e344a28115e' : FunctionalChainInvolvementLink 
                            connect source ::> 'eRod_Autonomous_Vehicle_2024 Project'::'eRod_Autonomous_Vehicle_2024'::'Logical Architecture'::'Logical Functions'::'Root Logical Function'.'Adaptive Cruise Control (ACC)'.'63c4b16b-8f2e-4cc8-8219-82b4992a9585'
                            to  target ::> 'eRod_Autonomous_Vehicle_2024 Project'::'eRod_Autonomous_Vehicle_2024'::'Logical Architecture'::'Logical Functions'::'Root Logical Function'.'Adaptive Cruise Control (ACC)'.'2fb5cd2b-3fec-4509-b6e6-9c7d2b431853' {

                                ref :>> involved = 'eRod_Autonomous_Vehicle_2024 Project'::'eRod_Autonomous_Vehicle_2024'::'Logical Architecture'::'Logical Functions'::'Root Logical Function'.'fe17c8d3-e8bb-40ed-bd81-e495271faa01';

                            } 
                        ref action '2d4cd1b9-dc3b-453e-991c-77c3ef5986b5' = 'eRod_Autonomous_Vehicle_2024 Project'::'eRod_Autonomous_Vehicle_2024'::'Logical Architecture'::'Logical Functions'::'Root Logical Function'.'Provide target vehicle velocity'; 
                        connection '5d2e66ce-0fbb-4326-818d-708dc5ddede8' : FunctionalChainInvolvementLink 
                            connect source ::> 'eRod_Autonomous_Vehicle_2024 Project'::'eRod_Autonomous_Vehicle_2024'::'Logical Architecture'::'Logical Functions'::'Root Logical Function'.'Adaptive Cruise Control (ACC)'.'2d4cd1b9-dc3b-453e-991c-77c3ef5986b5'
                            to  target ::> 'eRod_Autonomous_Vehicle_2024 Project'::'eRod_Autonomous_Vehicle_2024'::'Logical Architecture'::'Logical Functions'::'Root Logical Function'.'Adaptive Cruise Control (ACC)'.'2fb5cd2b-3fec-4509-b6e6-9c7d2b431853' {

                                ref :>> involved = 'eRod_Autonomous_Vehicle_2024 Project'::'eRod_Autonomous_Vehicle_2024'::'Logical Architecture'::'Logical Functions'::'Root Logical Function'.'2659f7a0-916a-49ea-9d12-eab9a18e2a75';

                            } 
                         
                    }  
                    action 'Lane Keep Assist (LKA)' : FunctionalChain  { 
                        @CapellaID { eid = "3f210c85-8eb8-46ef-bd31-f41b0c80e2c4"; } 
                        attribute :>> kind = FunctionalChainKind::SIMPLE; 
                        connection '294fb7ed-4f91-4b8e-a2d3-af76d0465921' : FunctionalChainInvolvementLink 
                            connect source ::> 'eRod_Autonomous_Vehicle_2024 Project'::'eRod_Autonomous_Vehicle_2024'::'Logical Architecture'::'Logical Functions'::'Root Logical Function'.'Lane Keep Assist (LKA)'.'f346d469-cab3-4736-98db-256b1d26b41f'
                            to  target ::> 'eRod_Autonomous_Vehicle_2024 Project'::'eRod_Autonomous_Vehicle_2024'::'Logical Architecture'::'Logical Functions'::'Root Logical Function'.'Lane Keep Assist (LKA)'.'ac107618-b461-4750-81e6-0f88a8b1eee3' {

                                ref :>> involved = 'eRod_Autonomous_Vehicle_2024 Project'::'eRod_Autonomous_Vehicle_2024'::'Logical Architecture'::'Logical Functions'::'Root Logical Function'.'73c0fd18-6786-4434-9f4c-6eec548197c5';

                            } 
                        ref action 'f346d469-cab3-4736-98db-256b1d26b41f' = 'eRod_Autonomous_Vehicle_2024 Project'::'eRod_Autonomous_Vehicle_2024'::'Logical Architecture'::'Logical Functions'::'Root Logical Function'.'Provide road markers'; 
                        connection 'ee34af11-e30e-46e4-b4c0-14018402adcd' : FunctionalChainInvolvementLink 
                            connect source ::> 'eRod_Autonomous_Vehicle_2024 Project'::'eRod_Autonomous_Vehicle_2024'::'Logical Architecture'::'Logical Functions'::'Root Logical Function'.'Lane Keep Assist (LKA)'.'3017f406-221d-40f1-8e23-190b2572003a'
                            to  target ::> 'eRod_Autonomous_Vehicle_2024 Project'::'eRod_Autonomous_Vehicle_2024'::'Logical Architecture'::'Logical Functions'::'Root Logical Function'.'Lane Keep Assist (LKA)'.'995f2f50-2d0c-4034-9fc1-dac9dd8e02b6' {

                                ref :>> involved = 'eRod_Autonomous_Vehicle_2024 Project'::'eRod_Autonomous_Vehicle_2024'::'Logical Architecture'::'Logical Functions'::'Root Logical Function'.'6dcb3416-8c5a-458c-875a-cd995816b985';

                            } 
                        ref action '995f2f50-2d0c-4034-9fc1-dac9dd8e02b6' = 'eRod_Autonomous_Vehicle_2024 Project'::'eRod_Autonomous_Vehicle_2024'::'Logical Architecture'::'Logical Functions'::'Root Logical Function'.'Automatic Steering'; 
                        connection 'ec20df4d-3ca9-49f8-b67c-d9dc23796c51' : FunctionalChainInvolvementLink 
                            connect source ::> 'eRod_Autonomous_Vehicle_2024 Project'::'eRod_Autonomous_Vehicle_2024'::'Logical Architecture'::'Logical Functions'::'Root Logical Function'.'Lane Keep Assist (LKA)'.'995f2f50-2d0c-4034-9fc1-dac9dd8e02b6'
                            to  target ::> 'eRod_Autonomous_Vehicle_2024 Project'::'eRod_Autonomous_Vehicle_2024'::'Logical Architecture'::'Logical Functions'::'Root Logical Function'.'Lane Keep Assist (LKA)'.'df94be03-596e-49c4-b425-1fed54ce47b1' {

                                ref :>> involved = 'eRod_Autonomous_Vehicle_2024 Project'::'eRod_Autonomous_Vehicle_2024'::'Logical Architecture'::'Logical Functions'::'Root Logical Function'.'774ae67e-2aeb-4f3a-8957-c8211a532afe';

                            } 
                        ref action 'df94be03-596e-49c4-b425-1fed54ce47b1' = 'eRod_Autonomous_Vehicle_2024 Project'::'eRod_Autonomous_Vehicle_2024'::'Logical Architecture'::'Logical Functions'::'Root Logical Function'.'Steer Wheels'; 
                        ref action 'ac107618-b461-4750-81e6-0f88a8b1eee3' = 'eRod_Autonomous_Vehicle_2024 Project'::'eRod_Autonomous_Vehicle_2024'::'Logical Architecture'::'Logical Functions'::'Root Logical Function'.'Detect road'.'Capture view'; 
                        ref action 'b856d768-b263-47b4-9686-2c5f66cc907e' = 'eRod_Autonomous_Vehicle_2024 Project'::'eRod_Autonomous_Vehicle_2024'::'Logical Architecture'::'Logical Functions'::'Root Logical Function'.'Detect road'.'Image fusion'; 
                        connection '2d6cfa4c-6fff-4e6f-ab9a-58cd6a72cfb2' : FunctionalChainInvolvementLink 
                            connect source ::> 'eRod_Autonomous_Vehicle_2024 Project'::'eRod_Autonomous_Vehicle_2024'::'Logical Architecture'::'Logical Functions'::'Root Logical Function'.'Lane Keep Assist (LKA)'.'ac107618-b461-4750-81e6-0f88a8b1eee3'
                            to  target ::> 'eRod_Autonomous_Vehicle_2024 Project'::'eRod_Autonomous_Vehicle_2024'::'Logical Architecture'::'Logical Functions'::'Root Logical Function'.'Lane Keep Assist (LKA)'.'b856d768-b263-47b4-9686-2c5f66cc907e' {

                                ref :>> involved = 'eRod_Autonomous_Vehicle_2024 Project'::'eRod_Autonomous_Vehicle_2024'::'Logical Architecture'::'Logical Functions'::'Root Logical Function'.'Detect road'.'9f74537d-58c1-4d86-8f5d-62cee58197d3';

                            } 
                        ref action '3017f406-221d-40f1-8e23-190b2572003a' = 'eRod_Autonomous_Vehicle_2024 Project'::'eRod_Autonomous_Vehicle_2024'::'Logical Architecture'::'Logical Functions'::'Root Logical Function'.'Detect road'.'Detect path'; 
                        connection '7303980c-6e82-4a4f-b2ae-33ef84db2715' : FunctionalChainInvolvementLink 
                            connect source ::> 'eRod_Autonomous_Vehicle_2024 Project'::'eRod_Autonomous_Vehicle_2024'::'Logical Architecture'::'Logical Functions'::'Root Logical Function'.'Lane Keep Assist (LKA)'.'b856d768-b263-47b4-9686-2c5f66cc907e'
                            to  target ::> 'eRod_Autonomous_Vehicle_2024 Project'::'eRod_Autonomous_Vehicle_2024'::'Logical Architecture'::'Logical Functions'::'Root Logical Function'.'Lane Keep Assist (LKA)'.'3017f406-221d-40f1-8e23-190b2572003a' {

                                ref :>> involved = 'eRod_Autonomous_Vehicle_2024 Project'::'eRod_Autonomous_Vehicle_2024'::'Logical Architecture'::'Logical Functions'::'Root Logical Function'.'362d23cd-3e2a-4128-8134-4de34e796267';

                            } 
                        ref action '796cf21d-fe11-4e4a-838d-2cf5a7180353' = 'eRod_Autonomous_Vehicle_2024 Project'::'eRod_Autonomous_Vehicle_2024'::'Logical Architecture'::'Logical Functions'::'Root Logical Function'.'Resist Front Wheels'; 
                        connection '024ceb0a-7b7a-488f-9e9d-fbdbf5cfdc0b' : FunctionalChainInvolvementLink 
                            connect source ::> 'eRod_Autonomous_Vehicle_2024 Project'::'eRod_Autonomous_Vehicle_2024'::'Logical Architecture'::'Logical Functions'::'Root Logical Function'.'Lane Keep Assist (LKA)'.'df94be03-596e-49c4-b425-1fed54ce47b1'
                            to  target ::> 'eRod_Autonomous_Vehicle_2024 Project'::'eRod_Autonomous_Vehicle_2024'::'Logical Architecture'::'Logical Functions'::'Root Logical Function'.'Lane Keep Assist (LKA)'.'796cf21d-fe11-4e4a-838d-2cf5a7180353' {

                                ref :>> involved = 'eRod_Autonomous_Vehicle_2024 Project'::'eRod_Autonomous_Vehicle_2024'::'Logical Architecture'::'Logical Functions'::'Root Logical Function'.'ae4ff77f-fec6-4f85-bbe6-cade3bb35824';

                            } 
                         
                    }  
                    action 'Vehicle Steering' : FunctionalChain  { 
                        @CapellaID { eid = "79e18381-1a48-489c-9940-aa08d75a6225"; } 
                        attribute :>> kind = FunctionalChainKind::SIMPLE; 
                        connection '79b80ba3-be53-4964-b3a4-9bee5adcfb32' : FunctionalChainInvolvementLink 
                            connect source ::> 'eRod_Autonomous_Vehicle_2024 Project'::'eRod_Autonomous_Vehicle_2024'::'Logical Architecture'::'Logical Functions'::'Root Logical Function'.'Vehicle Steering'.'9c27ce39-4ced-4013-9ae4-f8f1357bc778'
                            to  target ::> 'eRod_Autonomous_Vehicle_2024 Project'::'eRod_Autonomous_Vehicle_2024'::'Logical Architecture'::'Logical Functions'::'Root Logical Function'.'Vehicle Steering'.'15350f17-477b-48f7-bcbc-195435034516' {

                                ref :>> involved = 'eRod_Autonomous_Vehicle_2024 Project'::'eRod_Autonomous_Vehicle_2024'::'Logical Architecture'::'Logical Functions'::'Root Logical Function'.'4f4af8a7-2552-44e8-8765-3c593ad81912';

                            } 
                        ref action '15350f17-477b-48f7-bcbc-195435034516' = 'eRod_Autonomous_Vehicle_2024 Project'::'eRod_Autonomous_Vehicle_2024'::'Logical Architecture'::'Logical Functions'::'Root Logical Function'.'Steer Wheels'; 
                        ref action '9c27ce39-4ced-4013-9ae4-f8f1357bc778' = 'eRod_Autonomous_Vehicle_2024 Project'::'eRod_Autonomous_Vehicle_2024'::'Logical Architecture'::'Logical Functions'::'Root Logical Function'.'Drive vehicle'; 
                        connection 'e8ea7115-8278-499b-a886-c4088a639af1' : FunctionalChainInvolvementLink 
                            connect source ::> 'eRod_Autonomous_Vehicle_2024 Project'::'eRod_Autonomous_Vehicle_2024'::'Logical Architecture'::'Logical Functions'::'Root Logical Function'.'Vehicle Steering'.'15350f17-477b-48f7-bcbc-195435034516'
                            to  target ::> 'eRod_Autonomous_Vehicle_2024 Project'::'eRod_Autonomous_Vehicle_2024'::'Logical Architecture'::'Logical Functions'::'Root Logical Function'.'Vehicle Steering'.'9e487c6a-0a37-4242-8269-c0a23e28289b' {

                                ref :>> involved = 'eRod_Autonomous_Vehicle_2024 Project'::'eRod_Autonomous_Vehicle_2024'::'Logical Architecture'::'Logical Functions'::'Root Logical Function'.'ae4ff77f-fec6-4f85-bbe6-cade3bb35824';

                            } 
                        ref action '9e487c6a-0a37-4242-8269-c0a23e28289b' = 'eRod_Autonomous_Vehicle_2024 Project'::'eRod_Autonomous_Vehicle_2024'::'Logical Architecture'::'Logical Functions'::'Root Logical Function'.'Resist Front Wheels'; 
                         
                    }  
                    action 'Remote Park' : FunctionalChain  { 
                        @CapellaID { eid = "919f018b-ea50-4c71-8c29-5fa5792fadd1"; } 
                        attribute :>> kind = FunctionalChainKind::SIMPLE; 
                        connection '101a2366-1379-4782-8e67-561348986d4c' : FunctionalChainInvolvementLink 
                            connect source ::> 'eRod_Autonomous_Vehicle_2024 Project'::'eRod_Autonomous_Vehicle_2024'::'Logical Architecture'::'Logical Functions'::'Root Logical Function'.'Remote Park'.'7436f190-b750-4d92-873c-803cb41a95ed'
                            to  target ::> 'eRod_Autonomous_Vehicle_2024 Project'::'eRod_Autonomous_Vehicle_2024'::'Logical Architecture'::'Logical Functions'::'Root Logical Function'.'Remote Park'.'62e6e165-1e1b-4de9-a020-253596f2d8f9' {

                                ref :>> involved = 'eRod_Autonomous_Vehicle_2024 Project'::'eRod_Autonomous_Vehicle_2024'::'Logical Architecture'::'Logical Functions'::'Root Logical Function'.'301bd8ac-cfac-4b29-ad12-48ea68fcef3e';

                            } 
                        ref action '62e6e165-1e1b-4de9-a020-253596f2d8f9' = 'eRod_Autonomous_Vehicle_2024 Project'::'eRod_Autonomous_Vehicle_2024'::'Logical Architecture'::'Logical Functions'::'Root Logical Function'.'Remote Operate Car'; 
                        ref action '7436f190-b750-4d92-873c-803cb41a95ed' = 'eRod_Autonomous_Vehicle_2024 Project'::'eRod_Autonomous_Vehicle_2024'::'Logical Architecture'::'Logical Functions'::'Root Logical Function'.'Vehicle Command'; 
                        connection '10a6d9ce-33f3-411c-ac7b-a595c1ebd2be' : FunctionalChainInvolvementLink 
                            connect source ::> 'eRod_Autonomous_Vehicle_2024 Project'::'eRod_Autonomous_Vehicle_2024'::'Logical Architecture'::'Logical Functions'::'Root Logical Function'.'Remote Park'.'62e6e165-1e1b-4de9-a020-253596f2d8f9'
                            to  target ::> 'eRod_Autonomous_Vehicle_2024 Project'::'eRod_Autonomous_Vehicle_2024'::'Logical Architecture'::'Logical Functions'::'Root Logical Function'.'Remote Park'.'cf9f7648-e4b7-4754-9701-7314a6985ace' {

                                ref :>> involved = 'eRod_Autonomous_Vehicle_2024 Project'::'eRod_Autonomous_Vehicle_2024'::'Logical Architecture'::'Logical Functions'::'Root Logical Function'.'3ffc52b3-84cc-4e46-b9a1-73b4477f0db4';

                            } 
                        ref action 'cf9f7648-e4b7-4754-9701-7314a6985ace' = 'eRod_Autonomous_Vehicle_2024 Project'::'eRod_Autonomous_Vehicle_2024'::'Logical Architecture'::'Logical Functions'::'Root Logical Function'.'Park vehicle'; 
                        connection 'baa056ef-1f3f-4e33-8626-0bc18b129602' : FunctionalChainInvolvementLink 
                            connect source ::> 'eRod_Autonomous_Vehicle_2024 Project'::'eRod_Autonomous_Vehicle_2024'::'Logical Architecture'::'Logical Functions'::'Root Logical Function'.'Remote Park'.'cf9f7648-e4b7-4754-9701-7314a6985ace'
                            to  target ::> 'eRod_Autonomous_Vehicle_2024 Project'::'eRod_Autonomous_Vehicle_2024'::'Logical Architecture'::'Logical Functions'::'Root Logical Function'.'Remote Park'.'1e40c9fa-f5d4-4733-b1dd-366f6d699ea6' {

                                ref :>> involved = 'eRod_Autonomous_Vehicle_2024 Project'::'eRod_Autonomous_Vehicle_2024'::'Logical Architecture'::'Logical Functions'::'Root Logical Function'.'93262ba9-6596-4b5f-b46b-4fd1ddf0d744';

                            } 
                        ref action '5659f0dd-59f9-4bec-a77f-dc248a2241de' = 'eRod_Autonomous_Vehicle_2024 Project'::'eRod_Autonomous_Vehicle_2024'::'Logical Architecture'::'Logical Functions'::'Root Logical Function'.'Slow down and stop the vehicle'; 
                        connection 'd75f9f07-4a14-4654-9502-6bbc92674345' : FunctionalChainInvolvementLink 
                            connect source ::> 'eRod_Autonomous_Vehicle_2024 Project'::'eRod_Autonomous_Vehicle_2024'::'Logical Architecture'::'Logical Functions'::'Root Logical Function'.'Remote Park'.'cf9f7648-e4b7-4754-9701-7314a6985ace'
                            to  target ::> 'eRod_Autonomous_Vehicle_2024 Project'::'eRod_Autonomous_Vehicle_2024'::'Logical Architecture'::'Logical Functions'::'Root Logical Function'.'Remote Park'.'7423a7c0-3cdc-481d-bd34-14f48e1fc0ce' {

                                ref :>> involved = 'eRod_Autonomous_Vehicle_2024 Project'::'eRod_Autonomous_Vehicle_2024'::'Logical Architecture'::'Logical Functions'::'Root Logical Function'.'1dfbf83d-de25-4e27-8ccb-e14f31c3d4bd';

                            } 
                        ref action '7423a7c0-3cdc-481d-bd34-14f48e1fc0ce' = 'eRod_Autonomous_Vehicle_2024 Project'::'eRod_Autonomous_Vehicle_2024'::'Logical Architecture'::'Logical Functions'::'Root Logical Function'.'Steer Wheels Remote'; 
                        connection '83dcf922-3523-4a66-80ad-e8242043b6ad' : FunctionalChainInvolvementLink 
                            connect source ::> 'eRod_Autonomous_Vehicle_2024 Project'::'eRod_Autonomous_Vehicle_2024'::'Logical Architecture'::'Logical Functions'::'Root Logical Function'.'Remote Park'.'7423a7c0-3cdc-481d-bd34-14f48e1fc0ce'
                            to  target ::> 'eRod_Autonomous_Vehicle_2024 Project'::'eRod_Autonomous_Vehicle_2024'::'Logical Architecture'::'Logical Functions'::'Root Logical Function'.'Remote Park'.'b5211864-7787-4ba1-ae03-5a6b8c7d8060' {

                                ref :>> involved = 'eRod_Autonomous_Vehicle_2024 Project'::'eRod_Autonomous_Vehicle_2024'::'Logical Architecture'::'Logical Functions'::'Root Logical Function'.'065c228b-18bd-43b7-818c-46cd338ea62c';

                            } 
                        ref action 'b5211864-7787-4ba1-ae03-5a6b8c7d8060' = 'eRod_Autonomous_Vehicle_2024 Project'::'eRod_Autonomous_Vehicle_2024'::'Logical Architecture'::'Logical Functions'::'Root Logical Function'.'Deliver traction to surface'; 
                        connection '08b74ac8-cc23-4a78-8c6c-490a05e4fcf1' : FunctionalChainInvolvementLink 
                            connect source ::> 'eRod_Autonomous_Vehicle_2024 Project'::'eRod_Autonomous_Vehicle_2024'::'Logical Architecture'::'Logical Functions'::'Root Logical Function'.'Remote Park'.'b5211864-7787-4ba1-ae03-5a6b8c7d8060'
                            to  target ::> 'eRod_Autonomous_Vehicle_2024 Project'::'eRod_Autonomous_Vehicle_2024'::'Logical Architecture'::'Logical Functions'::'Root Logical Function'.'Remote Park'.'5458f28d-e761-4999-b18f-954d6576d251' {

                                ref :>> involved = 'eRod_Autonomous_Vehicle_2024 Project'::'eRod_Autonomous_Vehicle_2024'::'Logical Architecture'::'Logical Functions'::'Root Logical Function'.'3100499d-8657-4e28-a511-cf0fb745cfc4';

                            } 
                        ref action '5458f28d-e761-4999-b18f-954d6576d251' = 'eRod_Autonomous_Vehicle_2024 Project'::'eRod_Autonomous_Vehicle_2024'::'Logical Architecture'::'Logical Functions'::'Root Logical Function'.'Provide diverse terrain'; 
                        ref action '9065f828-72a3-4b20-87d0-417d69920464' = 'eRod_Autonomous_Vehicle_2024 Project'::'eRod_Autonomous_Vehicle_2024'::'Logical Architecture'::'Logical Functions'::'Root Logical Function'.'Status and command indication'; 
                        connection '5fae3fac-91b1-48f9-9ded-b085b215ca91' : FunctionalChainInvolvementLink 
                            connect source ::> 'eRod_Autonomous_Vehicle_2024 Project'::'eRod_Autonomous_Vehicle_2024'::'Logical Architecture'::'Logical Functions'::'Root Logical Function'.'Remote Park'.'9065f828-72a3-4b20-87d0-417d69920464'
                            to  target ::> 'eRod_Autonomous_Vehicle_2024 Project'::'eRod_Autonomous_Vehicle_2024'::'Logical Architecture'::'Logical Functions'::'Root Logical Function'.'Remote Park'.'cf9f7648-e4b7-4754-9701-7314a6985ace' {

                                ref :>> involved = 'eRod_Autonomous_Vehicle_2024 Project'::'eRod_Autonomous_Vehicle_2024'::'Logical Architecture'::'Logical Functions'::'Root Logical Function'.'1d236bc3-39f0-43d8-8426-1cf5bd694aac';

                            } 
                        ref action 'd540963f-0fdf-4cdc-a746-e48cfcc74bf4' = 'eRod_Autonomous_Vehicle_2024 Project'::'eRod_Autonomous_Vehicle_2024'::'Logical Architecture'::'Logical Functions'::'Root Logical Function'.'Receive Status of Progess '; 
                        connection '73d6f6f7-a686-46f7-9555-f62e858c5d57' : FunctionalChainInvolvementLink 
                            connect source ::> 'eRod_Autonomous_Vehicle_2024 Project'::'eRod_Autonomous_Vehicle_2024'::'Logical Architecture'::'Logical Functions'::'Root Logical Function'.'Remote Park'.'9065f828-72a3-4b20-87d0-417d69920464'
                            to  target ::> 'eRod_Autonomous_Vehicle_2024 Project'::'eRod_Autonomous_Vehicle_2024'::'Logical Architecture'::'Logical Functions'::'Root Logical Function'.'Remote Park'.'d540963f-0fdf-4cdc-a746-e48cfcc74bf4' {

                                ref :>> involved = 'eRod_Autonomous_Vehicle_2024 Project'::'eRod_Autonomous_Vehicle_2024'::'Logical Architecture'::'Logical Functions'::'Root Logical Function'.'bf6038d4-313e-4be9-b94c-1d69db48b20f';

                            } 
                        ref action '1e40c9fa-f5d4-4733-b1dd-366f6d699ea6' = 'eRod_Autonomous_Vehicle_2024 Project'::'eRod_Autonomous_Vehicle_2024'::'Logical Architecture'::'Logical Functions'::'Root Logical Function'.'Control Accel'; 
                         
                    }  
                    action 'Drive on a race track' : LogicalFunction  { 
                        @CapellaID { eid = "c1f18bcb-f1ac-4ede-abb7-37d532103e19"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outCommand' : FunctionOutputPort  { 
                            @CapellaID { eid = "9ee4cd50-517e-430d-8ced-03c33dcc494f"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'Drive on a race track'.'outCommand'); 
                    }  
                    action 'Sporty drive' : LogicalFunction  { 
                        @CapellaID { eid = "34c0d5db-e720-4053-b5cb-eae2084cba0f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 2' : FunctionOutputPort  { 
                            @CapellaID { eid = "890acbb7-ade0-41b5-9d27-259d0b8c40f8"; } 
                            attribute :>> isControl = false; 
                            attribute :>> isControlType = false; 
                            attribute :>> kindOfNode = ObjectNodeKind::Unspecified; 
                            attribute :>> ordering = ObjectNodeOrderingKind::FIFO; 
                             
                        }  
                        out port 'FOP 3' : FunctionOutputPort  { 
                            @CapellaID { eid = "a89583f3-8d13-45ec-97ac-07f3be55c0a0"; } 
                            attribute :>> isControl = false; 
                            attribute :>> isControlType = false; 
                            attribute :>> kindOfNode = ObjectNodeKind::Unspecified; 
                            attribute :>> ordering = ObjectNodeOrderingKind::FIFO; 
                        }  
                        in port 'FIP 2' : FunctionInputPort  { 
                            @CapellaID { eid = "d9d7fcce-952e-4ea0-b989-457b32151a77"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'Sporty drive'.'FOP 2',
                        'eRod_Autonomous_Vehicle_2024 Project'::'eRod_Autonomous_Vehicle_2024'::'Logical Architecture'::'Logical Functions'::'Root Logical Function'.'Sporty drive'.'FOP 3'); 
                        ref :>> inputs =  ('eRod_Autonomous_Vehicle_2024 Project'::'eRod_Autonomous_Vehicle_2024'::'Logical Architecture'::'Logical Functions'::'Root Logical Function'.'Sporty drive'.'FIP 2'); 
                        ref :>> availableInStates =  ('eRod_Autonomous_Vehicle_2024 Project'::'eRod_Autonomous_Vehicle_2024'::'Logical Architecture'::'Structure'::'eRod System'.'StateMachine 1'.'Still capable to finish car racing'); 
                    }  
                    action 'Car racing experience absorbed' : LogicalFunction  { 
                        @CapellaID { eid = "186fa02a-1d2b-4b99-9745-e493df88dad5"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'inProvide' : FunctionInputPort  { 
                            @CapellaID { eid = "79b8539d-d0d1-4c70-b13f-e4ddef2c4671"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Logical Architecture'::'Logical Functions'::'Root Logical Function'.'Car racing experience absorbed'.'inProvide'); 
                        ref :>> availableInStates =  ('eRod_Autonomous_Vehicle_2024 Project'::'eRod_Autonomous_Vehicle_2024'::'Logical Architecture'::'Structure'::'eRod System'.'StateMachine 1'.'Car racing experience absorbed'); 
                    }  
                    action 'Motor overheating warning ' : LogicalFunction  { 
                        @CapellaID { eid = "d759c68f-9dc7-4d6c-ae9c-f6bc3c4bf4e7"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outDisplay' : FunctionOutputPort  { 
                            @CapellaID { eid = "27f37fbd-c8ad-4d7f-be1e-7c75c8c88309"; } 
                            attribute :>> isControl = false; 
                            attribute :>> isControlType = false; 
                            attribute :>> kindOfNode = ObjectNodeKind::Unspecified; 
                            attribute :>> ordering = ObjectNodeOrderingKind::FIFO; 
                             
                        }  
                        in port 'inCause' : FunctionInputPort  { 
                            @CapellaID { eid = "6f97958c-d6d9-4a9d-82e4-9c68e639e5e1"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Motor overheating warning '.'outDisplay'); 
                        ref :>> inputs =  ('eRod_Autonomous_Vehicle_2024 Project'::'eRod_Autonomous_Vehicle_2024'::'Logical Architecture'::'Logical Functions'::'Root Logical Function'.'Motor overheating warning '.'inCause'); 
                        ref :>> availableInStates =  ('eRod_Autonomous_Vehicle_2024 Project'::'eRod_Autonomous_Vehicle_2024'::'Logical Architecture'::'Structure'::'eRod System'.'StateMachine 1'.'Display overheating warning'); 
                    }  
                    action 'Software update' : LogicalFunction  { 
                        @CapellaID { eid = "904f0c31-e36c-4337-9e30-3460a6c6fbd7"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outRe-enable' : FunctionOutputPort  { 
                            @CapellaID { eid = "a58d09fc-c0bb-4da6-88b9-1ee31f88bdb0"; } 
                            attribute :>> isControl = false; 
                            attribute :>> isControlType = false; 
                            attribute :>> kindOfNode = ObjectNodeKind::Unspecified; 
                            attribute :>> ordering = ObjectNodeOrderingKind::FIFO; 
                             
                        }  
                        in port 'inFeedback' : FunctionInputPort  { 
                            @CapellaID { eid = "84a92d0b-1683-47bc-ba74-36e6e21a7c0a"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Software update'.'outRe-enable'); 
                        ref :>> inputs =  ('eRod_Autonomous_Vehicle_2024 Project'::'eRod_Autonomous_Vehicle_2024'::'Logical Architecture'::'Logical Functions'::'Root Logical Function'.'Software update'.'inFeedback'); 
                    }  
                    action 'Report issues' : LogicalFunction  { 
                        @CapellaID { eid = "ad4ed5dd-8a09-47c3-ba8f-86e69a97bbf3"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "08ac894e-6c5d-43d3-a0c5-0391784d1629"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "cf2d505b-a3f5-4ac2-99e6-5b3045545fd9"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Report issues'.'FOP 1'); 
                        ref :>> inputs =  ('eRod_Autonomous_Vehicle_2024 Project'::'eRod_Autonomous_Vehicle_2024'::'Logical Architecture'::'Logical Functions'::'Root Logical Function'.'Report issues'.'FIP 1'); 
                        ref :>> availableInStates =  ('eRod_Autonomous_Vehicle_2024 Project'::'eRod_Autonomous_Vehicle_2024'::'Logical Architecture'::'Structure'::'eRod System'.'StateMachine 1'.'Driver get informed and report issues'); 
                    }  
                    action 'Get informed with issues' : LogicalFunction  { 
                        @CapellaID { eid = "dba09efa-67eb-4c70-860b-67804db09e5e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "00c8bd6b-fd14-489f-9ee2-bda4adc4f084"; } 
                            attribute :>> isControl = false; 
                            attribute :>> isControlType = false; 
                            attribute :>> kindOfNode = ObjectNodeKind::Unspecified; 
                            attribute :>> ordering = ObjectNodeOrderingKind::FIFO; 
                             
                        }  
                        in port 'inDisplay' : FunctionInputPort  { 
                            @CapellaID { eid = "c3ce424c-ceea-4bda-b203-366adefaf9e0"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Get informed with issues'.'FOP 1'); 
                        ref :>> inputs =  ('eRod_Autonomous_Vehicle_2024 Project'::'eRod_Autonomous_Vehicle_2024'::'Logical Architecture'::'Logical Functions'::'Root Logical Function'.'Get informed with issues'.'inDisplay'); 
                        ref :>> availableInStates =  ('eRod_Autonomous_Vehicle_2024 Project'::'eRod_Autonomous_Vehicle_2024'::'Logical Architecture'::'Structure'::'eRod System'.'StateMachine 1'.'Driver get informed and report issues'); 
                    }  
                    action 'Deaccelerate' : LogicalFunction  { 
                        @CapellaID { eid = "83fa6e0d-b4d9-4a90-9c59-4531449be004"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "be8a4d12-e4a3-4e8b-99e4-254a32ebdd95"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "869cd481-c0fa-4895-92a2-1a26eb4809b5"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Deaccelerate'.'FOP 1'); 
                        ref :>> inputs =  ('eRod_Autonomous_Vehicle_2024 Project'::'eRod_Autonomous_Vehicle_2024'::'Logical Architecture'::'Logical Functions'::'Root Logical Function'.'Deaccelerate'.'FIP 1'); 
                        ref :>> availableInStates =  ('eRod_Autonomous_Vehicle_2024 Project'::'eRod_Autonomous_Vehicle_2024'::'Logical Architecture'::'Structure'::'eRod System'.'StateMachine 1'.'Deacceleration'); 
                    }  
                    action 'Stop' : LogicalFunction  { 
                        @CapellaID { eid = "e256b848-e9c1-45ad-a743-aa6f5560495b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outProvide' : FunctionOutputPort  { 
                            @CapellaID { eid = "c91ef28a-d40c-4c2f-94ae-4275c682f8c6"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "992f9977-6a01-409d-be3c-c1b716a65448"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Stop'.'outProvide'); 
                        ref :>> inputs =  ('eRod_Autonomous_Vehicle_2024 Project'::'eRod_Autonomous_Vehicle_2024'::'Logical Architecture'::'Logical Functions'::'Root Logical Function'.'Stop'.'FIP 1'); 
                        ref :>> availableInStates =  ('eRod_Autonomous_Vehicle_2024 Project'::'eRod_Autonomous_Vehicle_2024'::'Logical Architecture'::'Structure'::'eRod System'.'StateMachine 1'.'Stop'); 
                    }  
                    action 'Get Software-update' : LogicalFunction  { 
                        @CapellaID { eid = "6ec29216-86bb-4476-9db7-4fd239e21c74"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "485bf8ba-775f-47d3-b08f-c9a5f72c0bc2"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "95086ea2-e391-433d-8ec4-514555db62b1"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "b6d0308f-adb7-445b-8f74-e80765b14884"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Get Software-update'.'FOP 1',
                        'eRod_Autonomous_Vehicle_2024 Project'::'eRod_Autonomous_Vehicle_2024'::'Logical Architecture'::'Logical Functions'::'Root Logical Function'.'Get Software-update'.'FOP 2'); 
                        ref :>> inputs =  ('eRod_Autonomous_Vehicle_2024 Project'::'eRod_Autonomous_Vehicle_2024'::'Logical Architecture'::'Logical Functions'::'Root Logical Function'.'Get Software-update'.'FIP 1'); 
                    }  
                    action 'Obtain car racing experience' : LogicalFunction  { 
                        @CapellaID { eid = "e49d217c-414c-419b-b8d4-03ad994bfc28"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "8fa7f2d2-d252-4262-bf65-4802d0c3d599"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "14a78201-db74-450d-86f0-f4918797bf6b"; } 
                            attribute :>> isControl = false; 
                            attribute :>> isControlType = false; 
                            attribute :>> kindOfNode = ObjectNodeKind::Unspecified; 
                            attribute :>> ordering = ObjectNodeOrderingKind::FIFO; 
                        }  
                         
                        ref :>> inputs =  ('eRod_Autonomous_Vehicle_2024 Project'::'eRod_Autonomous_Vehicle_2024'::'Logical Architecture'::'Logical Functions'::'Root Logical Function'.'Obtain car racing experience'.'FIP 1',
                        'eRod_Autonomous_Vehicle_2024 Project'::'eRod_Autonomous_Vehicle_2024'::'Logical Architecture'::'Logical Functions'::'Root Logical Function'.'Obtain car racing experience'.'FIP 2'); 
                        ref :>> availableInStates =  ('eRod_Autonomous_Vehicle_2024 Project'::'eRod_Autonomous_Vehicle_2024'::'Logical Architecture'::'Structure'::'eRod System'.'StateMachine 1'.'Driver obtain whole car racing experience'); 
                    }  
                    action 'Transfer Energy' : LogicalFunction  { 
                        @CapellaID { eid = "4e05bd16-472b-4412-b6ee-f07193c3033b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Acquire electrical Energy' : LogicalFunction  { 
                            @CapellaID { eid = "acd2be92-77d4-4357-b9c8-3bed60222725"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "475cbec0-f651-43fa-8114-0a51659fa8d5"; } 
                                attribute :>> isControl = false; 
                                attribute :>> isControlType = false; 
                                attribute :>> kindOfNode = ObjectNodeKind::Unspecified; 
                                attribute :>> ordering = ObjectNodeOrderingKind::FIFO; 
                                 
                            }  
                            out port 'FOP 2' : FunctionOutputPort  { 
                                @CapellaID { eid = "f1ca6bdf-494a-4e64-9119-55ab1d70abc6"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "9beee3a4-6011-4a78-a18a-58e8e6ebc9ff"; } 
                                attribute :>> isControl = false; 
                                attribute :>> isControlType = false; 
                                attribute :>> kindOfNode = ObjectNodeKind::Unspecified; 
                                attribute :>> ordering = ObjectNodeOrderingKind::FIFO; 
                                 
                            }  
                            in port 'FIP 2' : FunctionInputPort  { 
                                @CapellaID { eid = "2fec10d4-6353-4eaf-9c6f-2eceae8ddf04"; } 
                                attribute :>> isControl = false; 
                                attribute :>> isControlType = false; 
                                attribute :>> kindOfNode = ObjectNodeKind::Unspecified; 
                                attribute :>> ordering = ObjectNodeOrderingKind::FIFO; 
                            }  
                            in port 'FIP 3' : FunctionInputPort  { 
                                @CapellaID { eid = "702780fa-c001-45b3-96d5-f5f0a29e713f"; } 
                                attribute :>> isControl = false; 
                                attribute :>> isControlType = false; 
                                attribute :>> kindOfNode = ObjectNodeKind::Unspecified; 
                                attribute :>> ordering = ObjectNodeOrderingKind::FIFO; 
                            }  
                             
                            ref :>> outputs =  ('eRod_Autonomous_Vehicle_2024 Project'::'eRod_Autonomous_Vehicle_2024'::'Logical Architecture'::'Logical Functions'::'Root Logical Function'.'Transfer Energy'.'Acquire electrical Energy'.'FOP 1',
                            'eRod_Autonomous_Vehicle_2024 Project'::'eRod_Autonomous_Vehicle_2024'::'Logical Architecture'::'Logical Functions'::'Root Logical Function'.'Transfer Energy'.'Acquire electrical Energy'.'FOP 2'); 
                            ref :>> inputs =  ('eRod_Autonomous_Vehicle_2024 Project'::'eRod_Autonomous_Vehicle_2024'::'Logical Architecture'::'Logical Functions'::'Root Logical Function'.'Transfer Energy'.'Acquire electrical Energy'.'FIP 1',
                            'eRod_Autonomous_Vehicle_2024 Project'::'eRod_Autonomous_Vehicle_2024'::'Logical Architecture'::'Logical Functions'::'Root Logical Function'.'Transfer Energy'.'Acquire electrical Energy'.'FIP 2',
                            'eRod_Autonomous_Vehicle_2024 Project'::'eRod_Autonomous_Vehicle_2024'::'Logical Architecture'::'Logical Functions'::'Root Logical Function'.'Transfer Energy'.'Acquire electrical Energy'.'FIP 3'); 
                        }  
                        action 'Tranfer electrical energy into mechanical energy' : LogicalFunction  { 
                            @CapellaID { eid = "17e1b66f-b27b-4491-bce4-2699d428d6a5"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "f8a4abba-6d1c-4bd3-95bc-4a793b304f4a"; } 
                                attribute :>> isControl = false; 
                                attribute :>> isControlType = false; 
                                attribute :>> kindOfNode = ObjectNodeKind::Unspecified; 
                                attribute :>> ordering = ObjectNodeOrderingKind::FIFO; 
                                 
                            }  
                            out port 'FOP 2' : FunctionOutputPort  { 
                                @CapellaID { eid = "376b4389-3f54-46c0-b857-12d8f416b7a3"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Logical Architecture'::'Logical Functions'::'Root Logical Function'.'Transfer Energy'.'Tranfer electrical energy into mechanical energy'.'FOP 1',
                            'eRod_Autonomous_Vehicle_2024 Project'::'eRod_Autonomous_Vehicle_2024'::'Logical Architecture'::'Logical Functions'::'Root Logical Function'.'Transfer Energy'.'Tranfer electrical energy into mechanical energy'.'FOP 2'); 
                        }  
                        action 'Generate heat' : LogicalFunction  { 
                            @CapellaID { eid = "7796d90c-5620-4f5a-927a-0ed7971aea3d"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "a104be1b-3f8b-414a-9b29-753a6efd8f12"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "1c1c71f2-993a-4643-9bbb-518d11e96260"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Logical Architecture'::'Logical Functions'::'Root Logical Function'.'Transfer Energy'.'Generate heat'.'FOP 1'); 
                            ref :>> inputs =  ('eRod_Autonomous_Vehicle_2024 Project'::'eRod_Autonomous_Vehicle_2024'::'Logical Architecture'::'Logical Functions'::'Root Logical Function'.'Transfer Energy'.'Generate heat'.'FIP 1'); 
                        }  
                        interface 'b2bf2904-3822-49d1-bb65-eda87b66bb64' : FunctionalExchange 
                            connect source ::> 'eRod_Autonomous_Vehicle_2024 Project'::'eRod_Autonomous_Vehicle_2024'::'Logical Architecture'::'Logical Functions'::'Root Logical Function'.'Transfer Energy'.'Tranfer electrical energy into mechanical energy'.'FOP 1'
                            to target ::> 'eRod_Autonomous_Vehicle_2024 Project'::'eRod_Autonomous_Vehicle_2024'::'Logical Architecture'::'Logical Functions'::'Root Logical Function'.'Apply rotation on wheels'.'Energy' { 
                            @CapellaID { eid = "b2bf2904-3822-49d1-bb65-eda87b66bb64"; } 
                            attribute :>> isMulticast = false; 
                            attribute :>> isMultireceive = false; 
                            attribute :>> kindOfRate = RateKind::Unspecified; 
                            attribute :>> interfaceName = "Energy"; 
                             
                        }  
                        interface '0069f485-3d00-4d36-982f-5c6ee7e230fd' : FunctionalExchange 
                            connect source ::> 'eRod_Autonomous_Vehicle_2024 Project'::'eRod_Autonomous_Vehicle_2024'::'Logical Architecture'::'Logical Functions'::'Root Logical Function'.'Transfer Energy'.'Tranfer electrical energy into mechanical energy'.'FOP 2'
                            to target ::> 'eRod_Autonomous_Vehicle_2024 Project'::'eRod_Autonomous_Vehicle_2024'::'Logical Architecture'::'Logical Functions'::'Root Logical Function'.'Transfer Energy'.'Generate heat'.'FIP 1' { 
                            @CapellaID { eid = "0069f485-3d00-4d36-982f-5c6ee7e230fd"; } 
                            attribute :>> isMulticast = false; 
                            attribute :>> isMultireceive = false; 
                            attribute :>> kindOfRate = RateKind::Unspecified; 
                            attribute :>> interfaceName = "Energy"; 
                             
                        }  
                         
                        ref :>> ownedFunctions =  ('eRod_Autonomous_Vehicle_2024 Project'::'eRod_Autonomous_Vehicle_2024'::'Logical Architecture'::'Logical Functions'::'Root Logical Function'.'Transfer Energy'.'Acquire electrical Energy',
                        'eRod_Autonomous_Vehicle_2024 Project'::'eRod_Autonomous_Vehicle_2024'::'Logical Architecture'::'Logical Functions'::'Root Logical Function'.'Transfer Energy'.'Tranfer electrical energy into mechanical energy',
                        'eRod_Autonomous_Vehicle_2024 Project'::'eRod_Autonomous_Vehicle_2024'::'Logical Architecture'::'Logical Functions'::'Root Logical Function'.'Transfer Energy'.'Generate heat'); 
                        ref :>> ownedFunctionalExchanges =  ('eRod_Autonomous_Vehicle_2024 Project'::'eRod_Autonomous_Vehicle_2024'::'Logical Architecture'::'Logical Functions'::'Root Logical Function'.'Transfer Energy'.'b2bf2904-3822-49d1-bb65-eda87b66bb64',
                        'eRod_Autonomous_Vehicle_2024 Project'::'eRod_Autonomous_Vehicle_2024'::'Logical Architecture'::'Logical Functions'::'Root Logical Function'.'Transfer Energy'.'0069f485-3d00-4d36-982f-5c6ee7e230fd'); 
                    }  
                    action 'Motor protect' : LogicalFunction  { 
                        @CapellaID { eid = "73a30df6-464a-4344-a79c-231d7458b430"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Detect temperature limit' : LogicalFunction  { 
                            @CapellaID { eid = "990d81b3-0dc7-49d9-8719-f64e4302c0bb"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 3' : FunctionOutputPort  { 
                                @CapellaID { eid = "ddeb4a3a-828e-4402-8fe0-3e8079b33cf1"; } 
                                attribute :>> isControl = false; 
                                attribute :>> isControlType = false; 
                                attribute :>> kindOfNode = ObjectNodeKind::Unspecified; 
                                attribute :>> ordering = ObjectNodeOrderingKind::FIFO; 
                                 
                            }  
                            out port 'FOP 2' : FunctionOutputPort  { 
                                @CapellaID { eid = "1a5163ed-895c-4d51-9c9e-3b511949378a"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "9f160fad-2c39-4fb5-a5a0-07b3546aa46f"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Logical Architecture'::'Logical Functions'::'Root Logical Function'.'Motor protect'.'Detect temperature limit'.'FOP 3',
                            'eRod_Autonomous_Vehicle_2024 Project'::'eRod_Autonomous_Vehicle_2024'::'Logical Architecture'::'Logical Functions'::'Root Logical Function'.'Motor protect'.'Detect temperature limit'.'FOP 2'); 
                            ref :>> inputs =  ('eRod_Autonomous_Vehicle_2024 Project'::'eRod_Autonomous_Vehicle_2024'::'Logical Architecture'::'Logical Functions'::'Root Logical Function'.'Motor protect'.'Detect temperature limit'.'FIP 1'); 
                        }  
                        action 'Reduce power' : LogicalFunction  { 
                            @CapellaID { eid = "d1b89375-eebf-49e1-8b63-53e0787f5cd8"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "d61912c5-830b-458a-bfac-a33a6929b123"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "5b32cf5d-3978-4838-bfb7-3e71960d4b67"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('eRod_Autonomous_Vehicle_2024 Project'::'eRod_Autonomous_Vehicle_2024'::'Logical Architecture'::'Logical Functions'::'Root Logical Function'.'Motor protect'.'Reduce power'.'FOP 1'); 
                            ref :>> inputs =  ('eRod_Autonomous_Vehicle_2024 Project'::'eRod_Autonomous_Vehicle_2024'::'Logical Architecture'::'Logical Functions'::'Root Logical Function'.'Motor protect'.'Reduce power'.'FIP 1'); 
                        }  
                        action 'Monitor temperature' : LogicalFunction  { 
                            @CapellaID { eid = "da2a7287-5b00-400a-91d6-212e07db2a60"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 2' : FunctionOutputPort  { 
                                @CapellaID { eid = "d9c8e29e-8160-44b5-bb4d-ceed0889bc70"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "36bc7495-5202-4162-8287-71b4ae6fba00"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'Logical Architecture'::'Logical Functions'::'Root Logical Function'.'Motor protect'.'Monitor temperature'.'FOP 2'); 
                            ref :>> inputs =  ('eRod_Autonomous_Vehicle_2024 Project'::'eRod_Autonomous_Vehicle_2024'::'Logical Architecture'::'Logical Functions'::'Root Logical Function'.'Motor protect'.'Monitor temperature'.'FIP 1'); 
                        }  
                        interface 'ef57735d-e98b-466c-be56-d8fbca4ab801' : FunctionalExchange 
                            connect source ::> 'eRod_Autonomous_Vehicle_2024 Project'::'eRod_Autonomous_Vehicle_2024'::'Logical Architecture'::'Logical Functions'::'Root Logical Function'.'Motor protect'.'Monitor temperature'.'FOP 2'
                            to target ::> 'eRod_Autonomous_Vehicle_2024 Project'::'eRod_Autonomous_Vehicle_2024'::'Logical Architecture'::'Logical Functions'::'Root Logical Function'.'Motor protect'.'Detect temperature limit'.'FIP 1' { 
                            @CapellaID { eid = "ef57735d-e98b-466c-be56-d8fbca4ab801"; } 
                            attribute :>> isMulticast = false; 
                            attribute :>> isMultireceive = false; 
                            attribute :>> kindOfRate = RateKind::Unspecified; 
                            attribute :>> interfaceName = "Temperature"; 
                             
                        }  
                        interface '57378bfd-1c57-40f3-a130-a89cc2cc13d8' : FunctionalExchange 
                            connect source ::> 'eRod_Autonomous_Vehicle_2024 Project'::'eRod_Autonomous_Vehicle_2024'::'Logical Architecture'::'Logical Functions'::'Root Logical Function'.'Motor protect'.'Detect temperature limit'.'FOP 2'
                            to target ::> 'eRod_Autonomous_Vehicle_2024 Project'::'eRod_Autonomous_Vehicle_2024'::'Logical Architecture'::'Logical Functions'::'Root Logical Function'.'Motor protect'.'Reduce power'.'FIP 1' { 
                            @CapellaID { eid = "57378bfd-1c57-40f3-a130-a89cc2cc13d8"; } 
                            attribute :>> isMulticast = false; 
                            attribute :>> isMultireceive = false; 
                            attribute :>> kindOfRate = RateKind::Unspecified; 
                            attribute :>> interfaceName = "Signal"; 
                        }  
                         
                        ref :>> ownedFunctions =  ('eRod_Autonomous_Vehicle_2024 Project'::'eRod_Autonomous_Vehicle_2024'::'Logical Architecture'::'Logical Functions'::'Root Logical Function'.'Motor protect'.'Detect temperature limit',
                        'eRod_Autonomous_Vehicle_2024 Project'::'eRod_Autonomous_Vehicle_2024'::'Logical Architecture'::'Logical Functions'::'Root Logical Function'.'Motor protect'.'Reduce power',
                        'eRod_Autonomous_Vehicle_2024 Project'::'eRod_Autonomous_Vehicle_2024'::'Logical Architecture'::'Logical Functions'::'Root Logical Function'.'Motor protect'.'Monitor temperature'); 
                        ref :>> ownedFunctionalExchanges =  ('eRod_Autonomous_Vehicle_2024 Project'::'eRod_Autonomous_Vehicle_2024'::'Logical Architecture'::'Logical Functions'::'Root Logical Function'.'Motor protect'.'ef57735d-e98b-466c-be56-d8fbca4ab801',
                        'eRod_Autonomous_Vehicle_2024 Project'::'eRod_Autonomous_Vehicle_2024'::'Logical Architecture'::'Logical Functions'::'Root Logical Function'.'Motor protect'.'57378bfd-1c57-40f3-a130-a89cc2cc13d8'); 
                    }  
                    action 'Control temperature' : LogicalFunction  { 
                        @CapellaID { eid = "efb457b5-aa39-47b5-a191-875f47856abc"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Limit temperature' : LogicalFunction  { 
                            @CapellaID { eid = "fc5ecc5c-f856-4806-b3bb-396fb408908f"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "1cfa81fe-3f00-4fea-8eed-83d909068987"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "4fbe02d3-321a-4da0-83f3-ec111f517dde"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Logical Architecture'::'Logical Functions'::'Root Logical Function'.'Control temperature'.'Limit temperature'.'FOP 1'); 
                            ref :>> inputs =  ('eRod_Autonomous_Vehicle_2024 Project'::'eRod_Autonomous_Vehicle_2024'::'Logical Architecture'::'Logical Functions'::'Root Logical Function'.'Control temperature'.'Limit temperature'.'FIP 1'); 
                        }  
                        action 'Limit power' : LogicalFunction  { 
                            @CapellaID { eid = "7c36db7f-88a5-4a12-8d83-742e405ab9d4"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 2' : FunctionOutputPort  { 
                                @CapellaID { eid = "60815cc1-2854-4834-b7bb-396d2017c93f"; } 
                                attribute :>> isControl = false; 
                                attribute :>> isControlType = false; 
                                attribute :>> kindOfNode = ObjectNodeKind::Unspecified; 
                                attribute :>> ordering = ObjectNodeOrderingKind::FIFO; 
                            }  
                            out port 'FOP 1' : FunctionOutputPort  { 
                                @CapellaID { eid = "956ba504-45e2-4983-9f15-639fa549061c"; } 
                                attribute :>> isControl = false; 
                                attribute :>> isControlType = false; 
                                attribute :>> kindOfNode = ObjectNodeKind::Unspecified; 
                                attribute :>> ordering = ObjectNodeOrderingKind::FIFO; 
                                 
                            }  
                            in port 'Signal' : FunctionInputPort  { 
                                @CapellaID { eid = "77932a03-a7f4-4880-a163-4773f79be7c5"; } 
                                attribute :>> isControl = false; 
                                attribute :>> isControlType = false; 
                                attribute :>> kindOfNode = ObjectNodeKind::Unspecified; 
                                attribute :>> ordering = ObjectNodeOrderingKind::FIFO; 
                                 
                            }  
                            in port 'FIP 3' : FunctionInputPort  { 
                                @CapellaID { eid = "e07e69b9-76d7-42c7-95ad-9709e6ad4c4a"; } 
                                attribute :>> isControl = false; 
                                attribute :>> isControlType = false; 
                                attribute :>> kindOfNode = ObjectNodeKind::Unspecified; 
                                attribute :>> ordering = ObjectNodeOrderingKind::FIFO; 
                                 
                            }  
                            in port 'Command' : FunctionInputPort  { 
                                @CapellaID { eid = "6eb99764-cf0e-4420-8aad-8cce201e65f3"; } 
                                attribute :>> isControl = false; 
                                attribute :>> isControlType = false; 
                                attribute :>> kindOfNode = ObjectNodeKind::Unspecified; 
                                attribute :>> ordering = ObjectNodeOrderingKind::FIFO; 
                            }  
                             
                            ref :>> outputs =  ('eRod_Autonomous_Vehicle_2024 Project'::'eRod_Autonomous_Vehicle_2024'::'Logical Architecture'::'Logical Functions'::'Root Logical Function'.'Control temperature'.'Limit power'.'FOP 2',
                            'eRod_Autonomous_Vehicle_2024 Project'::'eRod_Autonomous_Vehicle_2024'::'Logical Architecture'::'Logical Functions'::'Root Logical Function'.'Control temperature'.'Limit power'.'FOP 1'); 
                            ref :>> inputs =  ('eRod_Autonomous_Vehicle_2024 Project'::'eRod_Autonomous_Vehicle_2024'::'Logical Architecture'::'Logical Functions'::'Root Logical Function'.'Control temperature'.'Limit power'.'Signal',
                            'eRod_Autonomous_Vehicle_2024 Project'::'eRod_Autonomous_Vehicle_2024'::'Logical Architecture'::'Logical Functions'::'Root Logical Function'.'Control temperature'.'Limit power'.'FIP 3',
                            'eRod_Autonomous_Vehicle_2024 Project'::'eRod_Autonomous_Vehicle_2024'::'Logical Architecture'::'Logical Functions'::'Root Logical Function'.'Control temperature'.'Limit power'.'Command'); 
                        }  
                        interface 'edb260a4-4f89-4dce-bf4e-6861be76c285' : FunctionalExchange 
                            connect source ::> 'eRod_Autonomous_Vehicle_2024 Project'::'eRod_Autonomous_Vehicle_2024'::'Logical Architecture'::'Logical Functions'::'Root Logical Function'.'Control temperature'.'Limit temperature'.'FOP 1'
                            to target ::> 'eRod_Autonomous_Vehicle_2024 Project'::'eRod_Autonomous_Vehicle_2024'::'Logical Architecture'::'Logical Functions'::'Root Logical Function'.'Control temperature'.'Limit power'.'Signal' { 
                            @CapellaID { eid = "edb260a4-4f89-4dce-bf4e-6861be76c285"; } 
                            attribute :>> isMulticast = false; 
                            attribute :>> isMultireceive = false; 
                            attribute :>> kindOfRate = RateKind::Unspecified; 
                            attribute :>> interfaceName = "Signal"; 
                             
                        }  
                         
                        ref :>> ownedFunctions =  ('eRod_Autonomous_Vehicle_2024 Project'::'eRod_Autonomous_Vehicle_2024'::'Logical Architecture'::'Logical Functions'::'Root Logical Function'.'Control temperature'.'Limit temperature',
                        'eRod_Autonomous_Vehicle_2024 Project'::'eRod_Autonomous_Vehicle_2024'::'Logical Architecture'::'Logical Functions'::'Root Logical Function'.'Control temperature'.'Limit power'); 
                        ref :>> ownedFunctionalExchanges =  ('eRod_Autonomous_Vehicle_2024 Project'::'eRod_Autonomous_Vehicle_2024'::'Logical Architecture'::'Logical Functions'::'Root Logical Function'.'Control temperature'.'edb260a4-4f89-4dce-bf4e-6861be76c285'); 
                    }  
                    action 'deliver mechanical power' : LogicalFunction  { 
                        @CapellaID { eid = "760d2572-b1cd-4864-841b-339ba682c590"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "3e00bded-f59f-451c-bad6-ee80f5b92e44"; } 
                            attribute :>> isControl = false; 
                            attribute :>> isControlType = false; 
                            attribute :>> kindOfNode = ObjectNodeKind::Unspecified; 
                            attribute :>> ordering = ObjectNodeOrderingKind::FIFO; 
                        }  
                        out port 'FOP 2' : FunctionOutputPort  { 
                            @CapellaID { eid = "da4bb73e-db5a-4cc9-ace7-21c1f0b8da11"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "8492231c-5d92-4bdc-b24b-6068dda3a9b8"; } 
                            attribute :>> isControl = false; 
                            attribute :>> isControlType = false; 
                            attribute :>> kindOfNode = ObjectNodeKind::Unspecified; 
                            attribute :>> ordering = ObjectNodeOrderingKind::FIFO; 
                             
                        }  
                        in port 'FIP 3' : FunctionInputPort  { 
                            @CapellaID { eid = "48ec8a9a-99af-4a94-b423-007f9d8aba03"; } 
                            attribute :>> isControl = false; 
                            attribute :>> isControlType = false; 
                            attribute :>> kindOfNode = ObjectNodeKind::Unspecified; 
                            attribute :>> ordering = ObjectNodeOrderingKind::FIFO; 
                             
                        }  
                        in port 'FIP 4' : FunctionInputPort  { 
                            @CapellaID { eid = "428f778a-08de-45ed-bd12-597e21dd0031"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'deliver mechanical power'.'FOP 1',
                        'eRod_Autonomous_Vehicle_2024 Project'::'eRod_Autonomous_Vehicle_2024'::'Logical Architecture'::'Logical Functions'::'Root Logical Function'.'deliver mechanical power'.'FOP 2'); 
                        ref :>> inputs =  ('eRod_Autonomous_Vehicle_2024 Project'::'eRod_Autonomous_Vehicle_2024'::'Logical Architecture'::'Logical Functions'::'Root Logical Function'.'deliver mechanical power'.'FIP 1',
                        'eRod_Autonomous_Vehicle_2024 Project'::'eRod_Autonomous_Vehicle_2024'::'Logical Architecture'::'Logical Functions'::'Root Logical Function'.'deliver mechanical power'.'FIP 3',
                        'eRod_Autonomous_Vehicle_2024 Project'::'eRod_Autonomous_Vehicle_2024'::'Logical Architecture'::'Logical Functions'::'Root Logical Function'.'deliver mechanical power'.'FIP 4'); 
                    }  
                    action 'Generate heat (Rotor)' : LogicalFunction  { 
                        @CapellaID { eid = "822eac73-7934-4223-b6e1-0ff94d246832"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "515a434d-7fa2-4d54-9477-7cd883c22651"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "751b3c48-71c1-4226-982d-231247e1d024"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'Generate heat (Rotor)'.'FOP 1'); 
                        ref :>> inputs =  ('eRod_Autonomous_Vehicle_2024 Project'::'eRod_Autonomous_Vehicle_2024'::'Logical Architecture'::'Logical Functions'::'Root Logical Function'.'Generate heat (Rotor)'.'FIP 1'); 
                    }  
                    action 'Provide magnetic field' : LogicalFunction  { 
                        @CapellaID { eid = "78fb2263-47a3-407d-bf07-67270f165d37"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "ff4d53b5-3807-4774-8b89-c470543f7d31"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "cc87d7bf-9aa1-4496-b39f-32fc654b56e1"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'Provide magnetic field'.'FOP 1'); 
                        ref :>> inputs =  ('eRod_Autonomous_Vehicle_2024 Project'::'eRod_Autonomous_Vehicle_2024'::'Logical Architecture'::'Logical Functions'::'Root Logical Function'.'Provide magnetic field'.'FIP 1'); 
                    }  
                    action 'Generate Heat (Stator)' : LogicalFunction  { 
                        @CapellaID { eid = "0291fcaa-2785-4f65-b862-3dbf10642a0f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "38263a07-8978-4927-8ec0-e78240c45cba"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "37ad856a-6ff9-44a6-be22-fd62db9b6653"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'Generate Heat (Stator)'.'FOP 1'); 
                        ref :>> inputs =  ('eRod_Autonomous_Vehicle_2024 Project'::'eRod_Autonomous_Vehicle_2024'::'Logical Architecture'::'Logical Functions'::'Root Logical Function'.'Generate Heat (Stator)'.'FIP 1'); 
                    }  
                    action 'protect' : LogicalFunction  { 
                        @CapellaID { eid = "5a3bd6c0-c963-43b4-90dc-6e3860a2589e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                         
                    }  
                    action 'Transfer heat' : LogicalFunction  { 
                        @CapellaID { eid = "8774be44-74a6-4cf7-aed9-bc774c50519e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "671ce975-aca4-4798-8691-ae67ad0d8014"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "55747264-a8e3-46d7-ba6f-82bf5359f273"; } 
                            attribute :>> isControl = false; 
                            attribute :>> isControlType = false; 
                            attribute :>> kindOfNode = ObjectNodeKind::Unspecified; 
                            attribute :>> ordering = ObjectNodeOrderingKind::FIFO; 
                        }  
                        action 'Monitor temperature' : LogicalFunction  { 
                            @CapellaID { eid = "8c6f6ea5-8107-4133-958d-fecfcc46118e"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            in port 'FIP 1' : FunctionInputPort  { 
                                @CapellaID { eid = "190de517-4ac3-4904-954b-e57e133ed841"; } 
                                attribute :>> isControl = false; 
                                attribute :>> isControlType = false; 
                                attribute :>> kindOfNode = ObjectNodeKind::Unspecified; 
                                attribute :>> ordering = ObjectNodeOrderingKind::FIFO; 
                                 
                            }  
                             
                            ref :>> inputs =  ('eRod_Autonomous_Vehicle_2024 Project'::'eRod_Autonomous_Vehicle_2024'::'Logical Architecture'::'Logical Functions'::'Root Logical Function'.'Transfer heat'.'Monitor temperature'.'FIP 1'); 
                        }  
                        action 'Reduce power' : LogicalFunction  { 
                            @CapellaID { eid = "3ac8c6a2-e911-4bfa-9c5e-6c95fa9da4db"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "2ec842e8-410b-4d49-ab80-ea38bd33553e"; } 
                                attribute :>> isControl = false; 
                                attribute :>> isControlType = false; 
                                attribute :>> kindOfNode = ObjectNodeKind::Unspecified; 
                                attribute :>> ordering = ObjectNodeOrderingKind::FIFO; 
                                 
                            }  
                            in port 'FIP 2' : FunctionInputPort  { 
                                @CapellaID { eid = "fc116461-a605-4a11-83ae-215df6224488"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Logical Architecture'::'Logical Functions'::'Root Logical Function'.'Transfer heat'.'Reduce power'.'FOP 1'); 
                            ref :>> inputs =  ('eRod_Autonomous_Vehicle_2024 Project'::'eRod_Autonomous_Vehicle_2024'::'Logical Architecture'::'Logical Functions'::'Root Logical Function'.'Transfer heat'.'Reduce power'.'FIP 2'); 
                        }  
                         
                        ref :>> outputs =  ('eRod_Autonomous_Vehicle_2024 Project'::'eRod_Autonomous_Vehicle_2024'::'Logical Architecture'::'Logical Functions'::'Root Logical Function'.'Transfer heat'.'FOP 1'); 
                        ref :>> inputs =  ('eRod_Autonomous_Vehicle_2024 Project'::'eRod_Autonomous_Vehicle_2024'::'Logical Architecture'::'Logical Functions'::'Root Logical Function'.'Transfer heat'.'FIP 1'); 
                        ref :>> ownedFunctions =  ('eRod_Autonomous_Vehicle_2024 Project'::'eRod_Autonomous_Vehicle_2024'::'Logical Architecture'::'Logical Functions'::'Root Logical Function'.'Transfer heat'.'Monitor temperature',
                        'eRod_Autonomous_Vehicle_2024 Project'::'eRod_Autonomous_Vehicle_2024'::'Logical Architecture'::'Logical Functions'::'Root Logical Function'.'Transfer heat'.'Reduce power'); 
                    }  
                    action 'Gather 21' : LogicalFunction  { 
                        @CapellaID { eid = "61e001ac-8147-4e64-b5d4-d6b81b06936e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::GATHER; 
                        attribute :>> isMaxInclusive = false; 
                        attribute :>> isMinInclusive = false; 
                        attribute :>> isOrdered = false; 
                        attribute :>> isUnique = false; 
                        out port 'FOP 1' : FunctionOutputPort  { 
                            @CapellaID { eid = "44017271-0ed3-4205-b047-1de5bdeb55a7"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "7dd9bc2b-2a67-47e4-9e82-a336c262a5aa"; } 
                            attribute :>> isControl = false; 
                            attribute :>> isControlType = false; 
                            attribute :>> kindOfNode = ObjectNodeKind::Unspecified; 
                            attribute :>> ordering = ObjectNodeOrderingKind::FIFO; 
                        }  
                        in port 'FIP 2' : FunctionInputPort  { 
                            @CapellaID { eid = "fc364174-c403-4bd6-b42b-144d439d0106"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'Logical Architecture'::'Logical Functions'::'Root Logical Function'.'Gather 21'.'FOP 1'); 
                        ref :>> inputs =  ('eRod_Autonomous_Vehicle_2024 Project'::'eRod_Autonomous_Vehicle_2024'::'Logical Architecture'::'Logical Functions'::'Root Logical Function'.'Gather 21'.'FIP 1',
                        'eRod_Autonomous_Vehicle_2024 Project'::'eRod_Autonomous_Vehicle_2024'::'Logical Architecture'::'Logical Functions'::'Root Logical Function'.'Gather 21'.'FIP 2'); 
                    }  
                    action 'Motor Start' : LogicalFunction  { 
                        @CapellaID { eid = "78d76baf-2d96-4f23-ab81-f6dc8ab863c3"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outCause' : FunctionOutputPort  { 
                            @CapellaID { eid = "5fa6ed7a-882c-415e-ba92-81800b835f3b"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "c83bf6ac-4367-4394-bb81-bb55643d5479"; } 
                            attribute :>> isControl = false; 
                            attribute :>> isControlType = false; 
                            attribute :>> kindOfNode = ObjectNodeKind::Unspecified; 
                            attribute :>> ordering = ObjectNodeOrderingKind::FIFO; 
                        }  
                        in port 'inRe-enable' : FunctionInputPort  { 
                            @CapellaID { eid = "16a08699-7dee-4a56-a4b3-4dc968fa9158"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Motor Start'.'outCause'); 
                        ref :>> inputs =  ('eRod_Autonomous_Vehicle_2024 Project'::'eRod_Autonomous_Vehicle_2024'::'Logical Architecture'::'Logical Functions'::'Root Logical Function'.'Motor Start'.'FIP 2',
                        'eRod_Autonomous_Vehicle_2024 Project'::'eRod_Autonomous_Vehicle_2024'::'Logical Architecture'::'Logical Functions'::'Root Logical Function'.'Motor Start'.'inRe-enable'); 
                    }  
                    action 'Transfer power to Axies' : LogicalFunction  { 
                        @CapellaID { eid = "2672e4c5-c09a-4140-8b28-ffd25632d1e1"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "46b45cfd-9f53-407b-9d58-c9572a2899b7"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "2b3fac41-b13e-4e76-ae9d-bd98740e848f"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'Transfer power to Axies'.'FOP 1'); 
                        ref :>> inputs =  ('eRod_Autonomous_Vehicle_2024 Project'::'eRod_Autonomous_Vehicle_2024'::'Logical Architecture'::'Logical Functions'::'Root Logical Function'.'Transfer power to Axies'.'FIP 1'); 
                    }  
                    action 'Apply rotation on wheels' : LogicalFunction  { 
                        @CapellaID { eid = "e54e22c7-55c3-4fef-b791-e9f29176e21e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 2' : FunctionOutputPort  { 
                            @CapellaID { eid = "d6959601-e110-4d81-b402-9cb9dd7451be"; } 
                            attribute :>> isControl = false; 
                            attribute :>> isControlType = false; 
                            attribute :>> kindOfNode = ObjectNodeKind::Unspecified; 
                            attribute :>> ordering = ObjectNodeOrderingKind::FIFO; 
                        }  
                        out port 'FOP 1' : FunctionOutputPort  { 
                            @CapellaID { eid = "6bfdd92f-bbb2-4140-a3f2-654baefc7659"; } 
                            attribute :>> isControl = false; 
                            attribute :>> isControlType = false; 
                            attribute :>> kindOfNode = ObjectNodeKind::Unspecified; 
                            attribute :>> ordering = ObjectNodeOrderingKind::FIFO; 
                             
                        }  
                        in port 'power' : FunctionInputPort  { 
                            @CapellaID { eid = "2cf386d6-52b5-4ad9-858c-e9d6327911ca"; } 
                            attribute :>> isControl = false; 
                            attribute :>> isControlType = false; 
                            attribute :>> kindOfNode = ObjectNodeKind::Unspecified; 
                            attribute :>> ordering = ObjectNodeOrderingKind::FIFO; 
                        }  
                        in port 'Energy' : FunctionInputPort  { 
                            @CapellaID { eid = "c4a8c0c3-621f-41ac-9eb2-a03819ca1bd3"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Apply rotation on wheels'.'FOP 2',
                        'eRod_Autonomous_Vehicle_2024 Project'::'eRod_Autonomous_Vehicle_2024'::'Logical Architecture'::'Logical Functions'::'Root Logical Function'.'Apply rotation on wheels'.'FOP 1'); 
                        ref :>> inputs =  ('eRod_Autonomous_Vehicle_2024 Project'::'eRod_Autonomous_Vehicle_2024'::'Logical Architecture'::'Logical Functions'::'Root Logical Function'.'Apply rotation on wheels'.'power',
                        'eRod_Autonomous_Vehicle_2024 Project'::'eRod_Autonomous_Vehicle_2024'::'Logical Architecture'::'Logical Functions'::'Root Logical Function'.'Apply rotation on wheels'.'Energy'); 
                    }  
                    action 'Split 25' : LogicalFunction  { 
                        @CapellaID { eid = "92e037a4-3759-4806-bbff-cc32f35157a2"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::SPLIT; 
                        attribute :>> isMaxInclusive = false; 
                        attribute :>> isMinInclusive = false; 
                        attribute :>> isOrdered = false; 
                        attribute :>> isUnique = false; 
                        out port 'FOP 1' : FunctionOutputPort  { 
                            @CapellaID { eid = "8e58dc7c-34f2-49d0-9b59-802e519ea08a"; } 
                            attribute :>> isControl = false; 
                            attribute :>> isControlType = false; 
                            attribute :>> kindOfNode = ObjectNodeKind::Unspecified; 
                            attribute :>> ordering = ObjectNodeOrderingKind::FIFO; 
                        }  
                        out port 'FOP 2' : FunctionOutputPort  { 
                            @CapellaID { eid = "86645672-b683-49ee-b4fe-83aa6bcfdaf4"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "c0c8bf4e-b5aa-4d8d-ba04-437b985c0098"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'Logical Architecture'::'Logical Functions'::'Root Logical Function'.'Split 25'.'FOP 1',
                        'eRod_Autonomous_Vehicle_2024 Project'::'eRod_Autonomous_Vehicle_2024'::'Logical Architecture'::'Logical Functions'::'Root Logical Function'.'Split 25'.'FOP 2'); 
                        ref :>> inputs =  ('eRod_Autonomous_Vehicle_2024 Project'::'eRod_Autonomous_Vehicle_2024'::'Logical Architecture'::'Logical Functions'::'Root Logical Function'.'Split 25'.'FIP 1'); 
                    }  
                    action 'Improve motor performance' : LogicalFunction  { 
                        @CapellaID { eid = "e09955f4-d42b-4e45-a099-1d52c49c8a84"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "731824fd-320e-4f93-8f76-d83266af3b27"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "7196573c-2c12-43b5-86be-1d74c9e6d70b"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'Improve motor performance'.'FOP 1'); 
                        ref :>> inputs =  ('eRod_Autonomous_Vehicle_2024 Project'::'eRod_Autonomous_Vehicle_2024'::'Logical Architecture'::'Logical Functions'::'Root Logical Function'.'Improve motor performance'.'FIP 1'); 
                    }  
                    action 'remote update' : LogicalFunction  { 
                        @CapellaID { eid = "ba700f11-90ba-409f-b619-d66e9a5c7b9f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "c4499d51-9a9d-4cc1-adad-f44f92372267"; } 
                            attribute :>> isControl = false; 
                            attribute :>> isControlType = false; 
                            attribute :>> kindOfNode = ObjectNodeKind::Unspecified; 
                            attribute :>> ordering = ObjectNodeOrderingKind::FIFO; 
                        }  
                         
                        ref :>> inputs =  ('eRod_Autonomous_Vehicle_2024 Project'::'eRod_Autonomous_Vehicle_2024'::'Logical Architecture'::'Logical Functions'::'Root Logical Function'.'remote update'.'FIP 1'); 
                    }  
                    action 'connected to the center' : LogicalFunction  { 
                        @CapellaID { eid = "f8bff57e-0847-40bb-80d5-c8d3abad7ad1"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "996b564c-ec46-4eed-bda1-9f3261e83b00"; } 
                            attribute :>> isControl = false; 
                            attribute :>> isControlType = false; 
                            attribute :>> kindOfNode = ObjectNodeKind::Unspecified; 
                            attribute :>> ordering = ObjectNodeOrderingKind::FIFO; 
                        }  
                        out port 'outRe-enable' : FunctionOutputPort  { 
                            @CapellaID { eid = "97b11654-7f4b-46cf-9dca-d8a40b1886d7"; } 
                            attribute :>> isControl = false; 
                            attribute :>> isControlType = false; 
                            attribute :>> kindOfNode = ObjectNodeKind::Unspecified; 
                            attribute :>> ordering = ObjectNodeOrderingKind::FIFO; 
                             
                        }  
                        in port 'inApproval' : FunctionInputPort  { 
                            @CapellaID { eid = "fbed326c-07d7-4834-97c5-7de5ef9893f1"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'connected to the center'.'FOP 1',
                        'eRod_Autonomous_Vehicle_2024 Project'::'eRod_Autonomous_Vehicle_2024'::'Logical Architecture'::'Logical Functions'::'Root Logical Function'.'connected to the center'.'outRe-enable'); 
                        ref :>> inputs =  ('eRod_Autonomous_Vehicle_2024 Project'::'eRod_Autonomous_Vehicle_2024'::'Logical Architecture'::'Logical Functions'::'Root Logical Function'.'connected to the center'.'inApproval'); 
                    }  
                    action 'Provide electrical energy' : LogicalFunction  { 
                        @CapellaID { eid = "f51476ae-2164-4701-be5a-ccd8c3269584"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "49c2daa8-b1b2-4df3-b287-a0d6754cccb6"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'Provide electrical energy'.'FOP 1'); 
                    }  
                    action 'Absorb bumps in the road' : LogicalFunction  { 
                        @CapellaID { eid = "a9fefd3c-649a-4c75-be24-88b4b38c6760"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Maximize the friction between the tires and roads' : LogicalFunction  { 
                        @CapellaID { eid = "a27a0588-0ff1-48e6-bcda-e6da5ca5239c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Light up the road' : LogicalFunction  { 
                        @CapellaID { eid = "0c206b14-5a6d-4085-a19c-d830b99c938f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Warn and show intent to other trafficants' : LogicalFunction  { 
                        @CapellaID { eid = "01fb551d-68c4-4920-ad72-b6e81d73aa7e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Turn on brake lights' : LogicalFunction  { 
                            @CapellaID { eid = "66351514-7a03-4532-a875-4d643eff61b4"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            in port 'FIP 1' : FunctionInputPort  { 
                                @CapellaID { eid = "29e89c97-75dd-467f-8ed6-8043ccbe5f1f"; } 
                                attribute :>> isControl = false; 
                                attribute :>> isControlType = false; 
                                attribute :>> kindOfNode = ObjectNodeKind::Unspecified; 
                                attribute :>> ordering = ObjectNodeOrderingKind::FIFO; 
                            }  
                            ref :>> inputs =  ('eRod_Autonomous_Vehicle_2024 Project'::'eRod_Autonomous_Vehicle_2024'::'Logical Architecture'::'Logical Functions'::'Root Logical Function'.'Warn and show intent to other trafficants'.'Turn on brake lights'.'FIP 1'); 
                        }  
                        ref :>> ownedFunctions =  ('eRod_Autonomous_Vehicle_2024 Project'::'eRod_Autonomous_Vehicle_2024'::'Logical Architecture'::'Logical Functions'::'Root Logical Function'.'Warn and show intent to other trafficants'.'Turn on brake lights'); 
                    }  
                    action 'Recieve feedback' : LogicalFunction  { 
                        @CapellaID { eid = "a7d8bfbb-eb6f-4746-aa75-3f287e59375c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outSolve' : FunctionOutputPort  { 
                            @CapellaID { eid = "449a8269-bec8-4db8-bd0d-5100631adb66"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "7c97dd73-f63d-4cfa-9919-510f39ada7ab"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'Recieve feedback'.'outSolve'); 
                        ref :>> inputs =  ('eRod_Autonomous_Vehicle_2024 Project'::'eRod_Autonomous_Vehicle_2024'::'Logical Architecture'::'Logical Functions'::'Root Logical Function'.'Recieve feedback'.'FIP 1'); 
                    }  
                    action 'Provide solution' : LogicalFunction  { 
                        @CapellaID { eid = "a4c33169-949b-4fac-81d0-f8959fc85c43"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outUpdate' : FunctionOutputPort  { 
                            @CapellaID { eid = "a6f89ea1-3813-422c-8752-f6f8e4463c06"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "9972188e-083a-4e39-8f34-d8bbea3a8d63"; } 
                            attribute :>> isControl = false; 
                            attribute :>> isControlType = false; 
                            attribute :>> kindOfNode = ObjectNodeKind::Unspecified; 
                            attribute :>> ordering = ObjectNodeOrderingKind::FIFO; 
                             
                        }  
                        in port 'inSolve' : FunctionInputPort  { 
                            @CapellaID { eid = "d928a0c5-981c-42af-a960-6e249462c604"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Provide solution'.'outUpdate',
                        'eRod_Autonomous_Vehicle_2024 Project'::'eRod_Autonomous_Vehicle_2024'::'Logical Architecture'::'Logical Functions'::'Root Logical Function'.'Provide solution'.'FOP 2'); 
                        ref :>> inputs =  ('eRod_Autonomous_Vehicle_2024 Project'::'eRod_Autonomous_Vehicle_2024'::'Logical Architecture'::'Logical Functions'::'Root Logical Function'.'Provide solution'.'inSolve'); 
                    }  
                    action 'Informed Software update' : LogicalFunction  { 
                        @CapellaID { eid = "37358780-9677-4f9c-8506-8ce37b2d62c1"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outApproval' : FunctionOutputPort  { 
                            @CapellaID { eid = "f3398a20-5c01-457b-b7ae-89b997c8b6fd"; } 
                            attribute :>> isControl = false; 
                            attribute :>> isControlType = false; 
                            attribute :>> kindOfNode = ObjectNodeKind::Unspecified; 
                            attribute :>> ordering = ObjectNodeOrderingKind::FIFO; 
                             
                        }  
                        in port 'inUpdate' : FunctionInputPort  { 
                            @CapellaID { eid = "7ff18f03-f911-4788-a837-a3ad77e69b04"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Informed Software update'.'outApproval'); 
                        ref :>> inputs =  ('eRod_Autonomous_Vehicle_2024 Project'::'eRod_Autonomous_Vehicle_2024'::'Logical Architecture'::'Logical Functions'::'Root Logical Function'.'Informed Software update'.'inUpdate'); 
                    }  
                    action 'Deliver traction to surface' : LogicalFunction  { 
                        @CapellaID { eid = "7e709252-470e-4b79-bb82-ceaa467d03de"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outTraction' : FunctionOutputPort  { 
                            @CapellaID { eid = "2bb310e9-d080-4b35-be66-07a3f1c0de82"; } 
                            attribute :>> isControl = false; 
                            attribute :>> isControlType = false; 
                            attribute :>> kindOfNode = ObjectNodeKind::Unspecified; 
                            attribute :>> ordering = ObjectNodeOrderingKind::FIFO; 
                             
                        }  
                        in port 'inDeceleration' : FunctionInputPort  { 
                            @CapellaID { eid = "42ffc52a-dc27-4fec-91c7-d3b8ea230946"; } 
                            attribute :>> isControl = false; 
                            attribute :>> isControlType = false; 
                            attribute :>> kindOfNode = ObjectNodeKind::Unspecified; 
                            attribute :>> ordering = ObjectNodeOrderingKind::FIFO; 
                             
                        }  
                        in port 'inWheel Position' : FunctionInputPort  { 
                            @CapellaID { eid = "7e74042d-3a32-41cd-ba58-487699a54384"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Deliver traction to surface'.'outTraction'); 
                        ref :>> inputs =  ('eRod_Autonomous_Vehicle_2024 Project'::'eRod_Autonomous_Vehicle_2024'::'Logical Architecture'::'Logical Functions'::'Root Logical Function'.'Deliver traction to surface'.'inDeceleration',
                        'eRod_Autonomous_Vehicle_2024 Project'::'eRod_Autonomous_Vehicle_2024'::'Logical Architecture'::'Logical Functions'::'Root Logical Function'.'Deliver traction to surface'.'inWheel Position'); 
                    }  
                    action 'Maintain distance' : LogicalFunction  { 
                        @CapellaID { eid = "1b97b1df-c5c3-42ac-b0cb-62f4b01f98c7"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "b0bc56bb-77f9-4fde-9e4d-276f49d1395f"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "7f46c6a2-fb02-4ae9-877e-bde13d2f4174"; } 
                            attribute :>> isControl = false; 
                            attribute :>> isControlType = false; 
                            attribute :>> kindOfNode = ObjectNodeKind::Unspecified; 
                            attribute :>> ordering = ObjectNodeOrderingKind::FIFO; 
                             
                        }  
                        out port 'FOP 3' : FunctionOutputPort  { 
                            @CapellaID { eid = "34bb4da3-ad48-4a21-bd61-638a8847aac1"; } 
                            attribute :>> isControl = false; 
                            attribute :>> isControlType = false; 
                            attribute :>> kindOfNode = ObjectNodeKind::Unspecified; 
                            attribute :>> ordering = ObjectNodeOrderingKind::FIFO; 
                             
                        }  
                        out port 'outActive braking' : FunctionOutputPort  { 
                            @CapellaID { eid = "30cdeee6-f948-42c8-8944-7d7fa135492a"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "617fa27d-3820-4933-8136-16681869af8f"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "57addd1a-9521-4e2a-9072-72e598d2aff1"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Maintain distance'.'FOP 1',
                        'eRod_Autonomous_Vehicle_2024 Project'::'eRod_Autonomous_Vehicle_2024'::'Logical Architecture'::'Logical Functions'::'Root Logical Function'.'Maintain distance'.'FOP 2',
                        'eRod_Autonomous_Vehicle_2024 Project'::'eRod_Autonomous_Vehicle_2024'::'Logical Architecture'::'Logical Functions'::'Root Logical Function'.'Maintain distance'.'FOP 3',
                        'eRod_Autonomous_Vehicle_2024 Project'::'eRod_Autonomous_Vehicle_2024'::'Logical Architecture'::'Logical Functions'::'Root Logical Function'.'Maintain distance'.'outActive braking'); 
                        ref :>> inputs =  ('eRod_Autonomous_Vehicle_2024 Project'::'eRod_Autonomous_Vehicle_2024'::'Logical Architecture'::'Logical Functions'::'Root Logical Function'.'Maintain distance'.'FIP 1',
                        'eRod_Autonomous_Vehicle_2024 Project'::'eRod_Autonomous_Vehicle_2024'::'Logical Architecture'::'Logical Functions'::'Root Logical Function'.'Maintain distance'.'FIP 2'); 
                    }  
                    action 'Slow down and stop the vehicle' : LogicalFunction  { 
                        @CapellaID { eid = "44f9211c-99ac-4ff4-96c1-d34ccea27738"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "85641c7a-fbaa-4021-b445-1043bb8d6405"; } 
                            attribute :>> isControl = false; 
                            attribute :>> isControlType = false; 
                            attribute :>> kindOfNode = ObjectNodeKind::Unspecified; 
                            attribute :>> ordering = ObjectNodeOrderingKind::FIFO; 
                             
                        }  
                        out port 'outDeceleration' : FunctionOutputPort  { 
                            @CapellaID { eid = "15a55a72-1b15-4174-b6f8-7ca849b90fe9"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "55a02642-c910-4c63-bb61-b3315802aaaf"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "55bd636a-492c-4f71-b91a-b1b97030b094"; } 
                            attribute :>> isControl = false; 
                            attribute :>> isControlType = false; 
                            attribute :>> kindOfNode = ObjectNodeKind::Unspecified; 
                            attribute :>> ordering = ObjectNodeOrderingKind::FIFO; 
                             
                        }  
                        in port 'FIP 3' : FunctionInputPort  { 
                            @CapellaID { eid = "eeb422b2-4e05-477f-a63e-48d48f66ff75"; } 
                            attribute :>> isControl = false; 
                            attribute :>> isControlType = false; 
                            attribute :>> kindOfNode = ObjectNodeKind::Unspecified; 
                            attribute :>> ordering = ObjectNodeOrderingKind::FIFO; 
                             
                        }  
                        in port 'FIP 4' : FunctionInputPort  { 
                            @CapellaID { eid = "99920594-05ae-445c-8eaa-756995476c6a"; } 
                            attribute :>> isControl = false; 
                            attribute :>> isControlType = false; 
                            attribute :>> kindOfNode = ObjectNodeKind::Unspecified; 
                            attribute :>> ordering = ObjectNodeOrderingKind::FIFO; 
                             
                        }  
                        in port 'inActive braking' : FunctionInputPort  { 
                            @CapellaID { eid = "71013c06-24d5-460a-bfb8-29fa4841bc2e"; } 
                            attribute :>> isControl = false; 
                            attribute :>> isControlType = false; 
                            attribute :>> kindOfNode = ObjectNodeKind::Unspecified; 
                            attribute :>> ordering = ObjectNodeOrderingKind::FIFO; 
                             
                        }  
                        in port 'FIP 7' : FunctionInputPort  { 
                            @CapellaID { eid = "11ccfbd5-d906-4052-9a27-cd3f7585d881"; } 
                            attribute :>> isControl = false; 
                            attribute :>> isControlType = false; 
                            attribute :>> kindOfNode = ObjectNodeKind::Unspecified; 
                            attribute :>> ordering = ObjectNodeOrderingKind::FIFO; 
                        }  
                        action 'Apply brakes' : LogicalFunction  { 
                            @CapellaID { eid = "f31c4015-c986-4708-8d41-58bb3453afd5"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            in port 'FIP 1' : FunctionInputPort  { 
                                @CapellaID { eid = "ea157c15-a79a-4dd5-bb55-c4847b8c4033"; } 
                                attribute :>> isControl = false; 
                                attribute :>> isControlType = false; 
                                attribute :>> kindOfNode = ObjectNodeKind::Unspecified; 
                                attribute :>> ordering = ObjectNodeOrderingKind::FIFO; 
                            }  
                            ref :>> inputs =  ('eRod_Autonomous_Vehicle_2024 Project'::'eRod_Autonomous_Vehicle_2024'::'Logical Architecture'::'Logical Functions'::'Root Logical Function'.'Slow down and stop the vehicle'.'Apply brakes'.'FIP 1'); 
                        }  
                        action 'Release brakes' : LogicalFunction  { 
                            @CapellaID { eid = "8cb610f9-f9a5-444c-a00a-c1059eabf00e"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            in port 'FIP 1' : FunctionInputPort  { 
                                @CapellaID { eid = "60aed8d0-8d52-42e7-9ce1-f35cb9d10b31"; } 
                                attribute :>> isControl = false; 
                                attribute :>> isControlType = false; 
                                attribute :>> kindOfNode = ObjectNodeKind::Unspecified; 
                                attribute :>> ordering = ObjectNodeOrderingKind::FIFO; 
                            }  
                            ref :>> inputs =  ('eRod_Autonomous_Vehicle_2024 Project'::'eRod_Autonomous_Vehicle_2024'::'Logical Architecture'::'Logical Functions'::'Root Logical Function'.'Slow down and stop the vehicle'.'Release brakes'.'FIP 1'); 
                        }  
                        action 'Measure brake force' : LogicalFunction  { 
                            @CapellaID { eid = "523e87e5-3982-4227-a98c-661ae451ef1f"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "7226b21e-9b8c-4565-85c4-e4ffc4b16fa0"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "e5c13632-ef91-4f74-8ce8-c031d372186f"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'Logical Architecture'::'Logical Functions'::'Root Logical Function'.'Slow down and stop the vehicle'.'Measure brake force'.'FOP 1'); 
                            ref :>> inputs =  ('eRod_Autonomous_Vehicle_2024 Project'::'eRod_Autonomous_Vehicle_2024'::'Logical Architecture'::'Logical Functions'::'Root Logical Function'.'Slow down and stop the vehicle'.'Measure brake force'.'FIP 1'); 
                        }  
                        action 'Detect locked wheels' : LogicalFunction  { 
                            @CapellaID { eid = "04996409-dc73-4cef-a5ab-e3ffcafc4198"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "629ede87-5030-40bd-af95-b9679c6de516"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "0f9cbda9-88b6-49ed-8259-664174cebd83"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'Logical Architecture'::'Logical Functions'::'Root Logical Function'.'Slow down and stop the vehicle'.'Detect locked wheels'.'FOP 1'); 
                            ref :>> inputs =  ('eRod_Autonomous_Vehicle_2024 Project'::'eRod_Autonomous_Vehicle_2024'::'Logical Architecture'::'Logical Functions'::'Root Logical Function'.'Slow down and stop the vehicle'.'Detect locked wheels'.'FIP 1'); 
                        }  
                        action 'Measure wheel rotation speed' : LogicalFunction  { 
                            @CapellaID { eid = "9c6d8571-7291-4390-8f84-59e020ad63a5"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "14ab77f8-90c0-4568-9310-2deea24c68a6"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'Logical Architecture'::'Logical Functions'::'Root Logical Function'.'Slow down and stop the vehicle'.'Measure wheel rotation speed'.'FOP 1'); 
                        }  
                        action 'Brake' : LogicalFunction  { 
                            @CapellaID { eid = "ccc239e4-d291-43f9-9ec2-fa5adad7aa67"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "0319ca8a-e034-4a99-90a9-3497518dbee7"; } 
                                attribute :>> isControl = false; 
                                attribute :>> isControlType = false; 
                                attribute :>> kindOfNode = ObjectNodeKind::Unspecified; 
                                attribute :>> ordering = ObjectNodeOrderingKind::FIFO; 
                            }  
                            out port 'FOP 2' : FunctionOutputPort  { 
                                @CapellaID { eid = "1aab1c3d-a01d-49c7-ab0c-e077742691e3"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "1470d40f-281d-42ab-ad89-02dc87843997"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'Logical Architecture'::'Logical Functions'::'Root Logical Function'.'Slow down and stop the vehicle'.'Brake'.'FOP 1',
                            'eRod_Autonomous_Vehicle_2024 Project'::'eRod_Autonomous_Vehicle_2024'::'Logical Architecture'::'Logical Functions'::'Root Logical Function'.'Slow down and stop the vehicle'.'Brake'.'FOP 2'); 
                            ref :>> inputs =  ('eRod_Autonomous_Vehicle_2024 Project'::'eRod_Autonomous_Vehicle_2024'::'Logical Architecture'::'Logical Functions'::'Root Logical Function'.'Slow down and stop the vehicle'.'Brake'.'FIP 1'); 
                        }  
                         
                        ref :>> outputs =  ('eRod_Autonomous_Vehicle_2024 Project'::'eRod_Autonomous_Vehicle_2024'::'Logical Architecture'::'Logical Functions'::'Root Logical Function'.'Slow down and stop the vehicle'.'FOP 1',
                        'eRod_Autonomous_Vehicle_2024 Project'::'eRod_Autonomous_Vehicle_2024'::'Logical Architecture'::'Logical Functions'::'Root Logical Function'.'Slow down and stop the vehicle'.'outDeceleration'); 
                        ref :>> inputs =  ('eRod_Autonomous_Vehicle_2024 Project'::'eRod_Autonomous_Vehicle_2024'::'Logical Architecture'::'Logical Functions'::'Root Logical Function'.'Slow down and stop the vehicle'.'FIP 1',
                        'eRod_Autonomous_Vehicle_2024 Project'::'eRod_Autonomous_Vehicle_2024'::'Logical Architecture'::'Logical Functions'::'Root Logical Function'.'Slow down and stop the vehicle'.'FIP 2',
                        'eRod_Autonomous_Vehicle_2024 Project'::'eRod_Autonomous_Vehicle_2024'::'Logical Architecture'::'Logical Functions'::'Root Logical Function'.'Slow down and stop the vehicle'.'FIP 3',
                        'eRod_Autonomous_Vehicle_2024 Project'::'eRod_Autonomous_Vehicle_2024'::'Logical Architecture'::'Logical Functions'::'Root Logical Function'.'Slow down and stop the vehicle'.'FIP 4',
                        'eRod_Autonomous_Vehicle_2024 Project'::'eRod_Autonomous_Vehicle_2024'::'Logical Architecture'::'Logical Functions'::'Root Logical Function'.'Slow down and stop the vehicle'.'inActive braking',
                        'eRod_Autonomous_Vehicle_2024 Project'::'eRod_Autonomous_Vehicle_2024'::'Logical Architecture'::'Logical Functions'::'Root Logical Function'.'Slow down and stop the vehicle'.'FIP 7'); 
                        ref :>> ownedFunctions =  ('eRod_Autonomous_Vehicle_2024 Project'::'eRod_Autonomous_Vehicle_2024'::'Logical Architecture'::'Logical Functions'::'Root Logical Function'.'Slow down and stop the vehicle'.'Apply brakes',
                        'eRod_Autonomous_Vehicle_2024 Project'::'eRod_Autonomous_Vehicle_2024'::'Logical Architecture'::'Logical Functions'::'Root Logical Function'.'Slow down and stop the vehicle'.'Release brakes',
                        'eRod_Autonomous_Vehicle_2024 Project'::'eRod_Autonomous_Vehicle_2024'::'Logical Architecture'::'Logical Functions'::'Root Logical Function'.'Slow down and stop the vehicle'.'Measure brake force',
                        'eRod_Autonomous_Vehicle_2024 Project'::'eRod_Autonomous_Vehicle_2024'::'Logical Architecture'::'Logical Functions'::'Root Logical Function'.'Slow down and stop the vehicle'.'Detect locked wheels',
                        'eRod_Autonomous_Vehicle_2024 Project'::'eRod_Autonomous_Vehicle_2024'::'Logical Architecture'::'Logical Functions'::'Root Logical Function'.'Slow down and stop the vehicle'.'Measure wheel rotation speed',
                        'eRod_Autonomous_Vehicle_2024 Project'::'eRod_Autonomous_Vehicle_2024'::'Logical Architecture'::'Logical Functions'::'Root Logical Function'.'Slow down and stop the vehicle'.'Brake'); 
                    }  
                    action 'Hold vehicle in place' : LogicalFunction  { 
                        @CapellaID { eid = "fafa3805-10a5-4939-b8cd-d3df41623baa"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Store energy' : LogicalFunction  { 
                        @CapellaID { eid = "c19451b7-2da5-4fa8-8bf6-930781100fb0"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Detect obstacles' : LogicalFunction  { 
                        @CapellaID { eid = "505ba340-510f-4330-85f9-f60b20da34d7"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "6b19684e-6066-4c62-9529-e2c46ec7673f"; } 
                            attribute :>> isControl = false; 
                            attribute :>> isControlType = false; 
                            attribute :>> kindOfNode = ObjectNodeKind::Unspecified; 
                            attribute :>> ordering = ObjectNodeOrderingKind::FIFO; 
                        }  
                        in port 'FIP 1' : FunctionInputPort  { 
                            @CapellaID { eid = "c317b7d0-7c4f-4b79-9091-5068258cf135"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'Logical Architecture'::'Logical Functions'::'Root Logical Function'.'Detect obstacles'.'FOP 1'); 
                        ref :>> inputs =  ('eRod_Autonomous_Vehicle_2024 Project'::'eRod_Autonomous_Vehicle_2024'::'Logical Architecture'::'Logical Functions'::'Root Logical Function'.'Detect obstacles'.'FIP 1'); 
                    }  
                    action 'Plan path' : LogicalFunction  { 
                        @CapellaID { eid = "e5c0f304-efed-47be-8543-fe5dc4f8fc36"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Drive route' : LogicalFunction  { 
                        @CapellaID { eid = "35e6ed4d-6f53-4590-a064-4cf46ac7616b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "b252c98b-00c7-49d3-9a5c-31d2979139f6"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'Logical Architecture'::'Logical Functions'::'Root Logical Function'.'Drive route'.'FOP 1'); 
                    }  
                    action 'Detect intersections' : LogicalFunction  { 
                        @CapellaID { eid = "44393978-4459-46de-a5f1-074d61e6ee0b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "62756847-2e08-4049-8311-08d1ab99f034"; } 
                            attribute :>> isControl = false; 
                            attribute :>> isControlType = false; 
                            attribute :>> kindOfNode = ObjectNodeKind::Unspecified; 
                            attribute :>> ordering = ObjectNodeOrderingKind::FIFO; 
                        }  
                        ref :>> inputs =  ('eRod_Autonomous_Vehicle_2024 Project'::'eRod_Autonomous_Vehicle_2024'::'Logical Architecture'::'Logical Functions'::'Root Logical Function'.'Detect intersections'.'FIP 1'); 
                    }  
                    action 'Detect signs' : LogicalFunction  { 
                        @CapellaID { eid = "97a7fa1f-3cb2-4557-8fc0-f8b6ffae6b4f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "9d842a3d-1fa1-4c45-8add-af1a839711a9"; } 
                            attribute :>> isControl = false; 
                            attribute :>> isControlType = false; 
                            attribute :>> kindOfNode = ObjectNodeKind::Unspecified; 
                            attribute :>> ordering = ObjectNodeOrderingKind::FIFO; 
                        }  
                        ref :>> inputs =  ('eRod_Autonomous_Vehicle_2024 Project'::'eRod_Autonomous_Vehicle_2024'::'Logical Architecture'::'Logical Functions'::'Root Logical Function'.'Detect signs'.'FIP 1'); 
                    }  
                    action 'Detect lights' : LogicalFunction  { 
                        @CapellaID { eid = "7c25ff97-6b85-45c4-9ede-b3ff06af2f60"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "a070c656-18a3-401f-a865-9b47008b025d"; } 
                            attribute :>> isControl = false; 
                            attribute :>> isControlType = false; 
                            attribute :>> kindOfNode = ObjectNodeKind::Unspecified; 
                            attribute :>> ordering = ObjectNodeOrderingKind::FIFO; 
                        }  
                        ref :>> inputs =  ('eRod_Autonomous_Vehicle_2024 Project'::'eRod_Autonomous_Vehicle_2024'::'Logical Architecture'::'Logical Functions'::'Root Logical Function'.'Detect lights'.'FIP 1'); 
                    }  
                    action 'Capture points' : LogicalFunction  { 
                        @CapellaID { eid = "f3273417-2cff-40f9-868b-c6f7e8d017c7"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "1ac04638-0b0c-4f90-86af-aee15b27f150"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'Logical Architecture'::'Logical Functions'::'Root Logical Function'.'Capture points'.'FOP 1'); 
                    }  
                    action 'Capture radar echo' : LogicalFunction  { 
                        @CapellaID { eid = "98b2fcb1-757e-46b2-b81e-0b8ea9406962"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "726b36f5-5344-42f0-913f-b4781c39592a"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'Logical Architecture'::'Logical Functions'::'Root Logical Function'.'Capture radar echo'.'FOP 1'); 
                    }  
                    action 'Avoid collision' : LogicalFunction  { 
                        @CapellaID { eid = "8eb29247-cffb-4849-82d3-926d4b9a927a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "cf37a206-03c5-4d4d-8aee-421dbacf8ede"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "0293d6a3-2ad4-4a17-bf12-f125dd94e15f"; } 
                            attribute :>> isControl = false; 
                            attribute :>> isControlType = false; 
                            attribute :>> kindOfNode = ObjectNodeKind::Unspecified; 
                            attribute :>> ordering = ObjectNodeOrderingKind::FIFO; 
                             
                        }  
                        out port 'FOP 3' : FunctionOutputPort  { 
                            @CapellaID { eid = "22de8fb2-e531-49a7-90a5-a71109742e0b"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "ea08e961-ce9d-48a0-9a82-5337e416e488"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Avoid collision'.'FOP 1',
                        'eRod_Autonomous_Vehicle_2024 Project'::'eRod_Autonomous_Vehicle_2024'::'Logical Architecture'::'Logical Functions'::'Root Logical Function'.'Avoid collision'.'FOP 2',
                        'eRod_Autonomous_Vehicle_2024 Project'::'eRod_Autonomous_Vehicle_2024'::'Logical Architecture'::'Logical Functions'::'Root Logical Function'.'Avoid collision'.'FOP 3'); 
                        ref :>> inputs =  ('eRod_Autonomous_Vehicle_2024 Project'::'eRod_Autonomous_Vehicle_2024'::'Logical Architecture'::'Logical Functions'::'Root Logical Function'.'Avoid collision'.'FIP 1'); 
                    }  
                    action 'Provide object location' : LogicalFunction  { 
                        @CapellaID { eid = "2eae265d-7063-4bec-a60c-91c2c4a24972"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "8096cfea-cf6a-4db0-83c7-895cae71c51c"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "77193a8c-370a-49a8-ac8d-e70f5a04d591"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'Provide object location'.'FOP 1'); 
                        ref :>> inputs =  ('eRod_Autonomous_Vehicle_2024 Project'::'eRod_Autonomous_Vehicle_2024'::'Logical Architecture'::'Logical Functions'::'Root Logical Function'.'Provide object location'.'FIP 1'); 
                    }  
                    action 'Observe status' : LogicalFunction  { 
                        @CapellaID { eid = "45086bb5-0bc3-488d-ab45-79034025a30b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "35665d5f-f1b1-4639-9b37-12db95f2f76c"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Logical Architecture'::'Logical Functions'::'Root Logical Function'.'Observe status'.'FIP 1'); 
                    }  
                    action 'Provide vehicle status' : LogicalFunction  { 
                        @CapellaID { eid = "8b76d9f3-192d-4265-adc3-2138a7bb0ff7"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "0ebdc9db-e941-4691-a9dc-c312b714c92e"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "0c1fdfb0-d392-4726-84cd-e40c05cb63d2"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Provide vehicle status'.'FOP 1'); 
                        ref :>> inputs =  ('eRod_Autonomous_Vehicle_2024 Project'::'eRod_Autonomous_Vehicle_2024'::'Logical Architecture'::'Logical Functions'::'Root Logical Function'.'Provide vehicle status'.'FIP 1'); 
                    }  
                    action 'Steer Wheels' : LogicalFunction  { 
                        @CapellaID { eid = "a50d7596-9440-4459-98b4-0ff59ec87171"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "33bad54a-197f-4ed0-9b2d-97fedfd60107"; } 
                            attribute :>> isControl = false; 
                            attribute :>> isControlType = false; 
                            attribute :>> kindOfNode = ObjectNodeKind::Unspecified; 
                            attribute :>> ordering = ObjectNodeOrderingKind::FIFO; 
                             
                        }  
                        in port 'Steer Angle' : FunctionInputPort  { 
                            @CapellaID { eid = "557eb60d-86f8-45b4-a5ad-7d0251c2ebac"; } 
                            attribute :>> isControl = false; 
                            attribute :>> isControlType = false; 
                            attribute :>> kindOfNode = ObjectNodeKind::Unspecified; 
                            attribute :>> ordering = ObjectNodeOrderingKind::FIFO; 
                        }  
                        in port 'Steer Command' : FunctionInputPort  { 
                            @CapellaID { eid = "af06289b-dc12-4f12-8196-44371f4cc968"; } 
                            attribute :>> isControl = false; 
                            attribute :>> isControlType = false; 
                            attribute :>> kindOfNode = ObjectNodeKind::Unspecified; 
                            attribute :>> ordering = ObjectNodeOrderingKind::FIFO; 
                             
                        }  
                        in port 'Auto Steer' : FunctionInputPort  { 
                            @CapellaID { eid = "68e33262-dd2f-43a7-b07b-5b977fa8f80d"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'Steer Wheels'.'FOP 1'); 
                        ref :>> inputs =  ('eRod_Autonomous_Vehicle_2024 Project'::'eRod_Autonomous_Vehicle_2024'::'Logical Architecture'::'Logical Functions'::'Root Logical Function'.'Steer Wheels'.'Steer Angle',
                        'eRod_Autonomous_Vehicle_2024 Project'::'eRod_Autonomous_Vehicle_2024'::'Logical Architecture'::'Logical Functions'::'Root Logical Function'.'Steer Wheels'.'Steer Command',
                        'eRod_Autonomous_Vehicle_2024 Project'::'eRod_Autonomous_Vehicle_2024'::'Logical Architecture'::'Logical Functions'::'Root Logical Function'.'Steer Wheels'.'Auto Steer'); 
                    }  
                    action 'Measure vehicle speed' : LogicalFunction  { 
                        @CapellaID { eid = "0f3cb2f9-e577-4398-a1fa-287d82d5731b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Locate targets' : LogicalFunction  { 
                        @CapellaID { eid = "ffd21560-0a3e-4e1e-9de3-3b2f82524540"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "7cbaa064-376c-45ef-90d5-6aaefcd31789"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "3c3892b6-f20a-481c-ae5a-d771ca5c6417"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "36a2925a-7099-4563-bb20-b191f839ad4f"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "472415e0-10a7-44a4-86c6-d9c935bbe9a5"; } 
                            attribute :>> isControl = false; 
                            attribute :>> isControlType = false; 
                            attribute :>> kindOfNode = ObjectNodeKind::Unspecified; 
                            attribute :>> ordering = ObjectNodeOrderingKind::FIFO; 
                             
                        }  
                        in port 'FIP 3' : FunctionInputPort  { 
                            @CapellaID { eid = "4491d4a9-6d19-4d5d-a91f-b8797600409e"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Locate targets'.'FOP 1',
                        'eRod_Autonomous_Vehicle_2024 Project'::'eRod_Autonomous_Vehicle_2024'::'Logical Architecture'::'Logical Functions'::'Root Logical Function'.'Locate targets'.'FOP 2'); 
                        ref :>> inputs =  ('eRod_Autonomous_Vehicle_2024 Project'::'eRod_Autonomous_Vehicle_2024'::'Logical Architecture'::'Logical Functions'::'Root Logical Function'.'Locate targets'.'FIP 1',
                        'eRod_Autonomous_Vehicle_2024 Project'::'eRod_Autonomous_Vehicle_2024'::'Logical Architecture'::'Logical Functions'::'Root Logical Function'.'Locate targets'.'FIP 2',
                        'eRod_Autonomous_Vehicle_2024 Project'::'eRod_Autonomous_Vehicle_2024'::'Logical Architecture'::'Logical Functions'::'Root Logical Function'.'Locate targets'.'FIP 3'); 
                    }  
                    action 'Maintain speed' : LogicalFunction  { 
                        @CapellaID { eid = "79ea3129-7fb4-4a8f-bb42-6f4c6737ca4e"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "613a785f-747d-41ef-b18b-ab51632d159a"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "cab994ca-17d0-4054-ab39-62aa2f2505e6"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Logical Architecture'::'Logical Functions'::'Root Logical Function'.'Maintain speed'.'FIP 1',
                        'eRod_Autonomous_Vehicle_2024 Project'::'eRod_Autonomous_Vehicle_2024'::'Logical Architecture'::'Logical Functions'::'Root Logical Function'.'Maintain speed'.'FIP 2'); 
                    }  
                    action 'Drive vehicle' : LogicalFunction  { 
                        @CapellaID { eid = "f6b02377-d86c-44db-abb1-ebcd9c3bef07"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "6ad19644-2237-4576-be1f-de4719c3994f"; } 
                            attribute :>> isControl = false; 
                            attribute :>> isControlType = false; 
                            attribute :>> kindOfNode = ObjectNodeKind::Unspecified; 
                            attribute :>> ordering = ObjectNodeOrderingKind::FIFO; 
                        }  
                        out port 'FOP 2' : FunctionOutputPort  { 
                            @CapellaID { eid = "8e26c018-8553-4c10-b46a-fb0abc907bb5"; } 
                            attribute :>> isControl = false; 
                            attribute :>> isControlType = false; 
                            attribute :>> kindOfNode = ObjectNodeKind::Unspecified; 
                            attribute :>> ordering = ObjectNodeOrderingKind::FIFO; 
                        }  
                        out port 'FOP 3' : FunctionOutputPort  { 
                            @CapellaID { eid = "907dcd60-d9b7-4540-aaa6-65d8df9fc9c6"; } 
                            attribute :>> isControl = false; 
                            attribute :>> isControlType = false; 
                            attribute :>> kindOfNode = ObjectNodeKind::Unspecified; 
                            attribute :>> ordering = ObjectNodeOrderingKind::FIFO; 
                             
                        }  
                        out port 'outLocation' : FunctionOutputPort  { 
                            @CapellaID { eid = "7f378b3f-8f82-4de4-ad00-009e1cb0fdfb"; } 
                            attribute :>> isControl = false; 
                            attribute :>> isControlType = false; 
                            attribute :>> kindOfNode = ObjectNodeKind::Unspecified; 
                            attribute :>> ordering = ObjectNodeOrderingKind::FIFO; 
                             
                        }  
                        in port 'inTerrain' : FunctionInputPort  { 
                            @CapellaID { eid = "0005bf69-6bcf-4f53-b266-3d6af6076da5"; } 
                            attribute :>> isControl = false; 
                            attribute :>> isControlType = false; 
                            attribute :>> kindOfNode = ObjectNodeKind::Unspecified; 
                            attribute :>> ordering = ObjectNodeOrderingKind::FIFO; 
                             
                        }  
                        in port 'inObjects' : FunctionInputPort  { 
                            @CapellaID { eid = "7d4581fd-fd9f-400b-990f-05295b8ae17a"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Drive vehicle'.'FOP 1',
                        'eRod_Autonomous_Vehicle_2024 Project'::'eRod_Autonomous_Vehicle_2024'::'Logical Architecture'::'Logical Functions'::'Root Logical Function'.'Drive vehicle'.'FOP 2',
                        'eRod_Autonomous_Vehicle_2024 Project'::'eRod_Autonomous_Vehicle_2024'::'Logical Architecture'::'Logical Functions'::'Root Logical Function'.'Drive vehicle'.'FOP 3',
                        'eRod_Autonomous_Vehicle_2024 Project'::'eRod_Autonomous_Vehicle_2024'::'Logical Architecture'::'Logical Functions'::'Root Logical Function'.'Drive vehicle'.'outLocation'); 
                        ref :>> inputs =  ('eRod_Autonomous_Vehicle_2024 Project'::'eRod_Autonomous_Vehicle_2024'::'Logical Architecture'::'Logical Functions'::'Root Logical Function'.'Drive vehicle'.'inTerrain',
                        'eRod_Autonomous_Vehicle_2024 Project'::'eRod_Autonomous_Vehicle_2024'::'Logical Architecture'::'Logical Functions'::'Root Logical Function'.'Drive vehicle'.'inObjects'); 
                    }  
                    action 'Automatic Steering' : LogicalFunction  { 
                        @CapellaID { eid = "c27a88ea-d0b3-4ae2-879c-a9ceaa897120"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "b29bfc65-15b8-47df-9424-54623bb6cc51"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "93eef238-5966-4f4b-ae9f-d70f0853219a"; } 
                            attribute :>> isControl = false; 
                            attribute :>> isControlType = false; 
                            attribute :>> kindOfNode = ObjectNodeKind::Unspecified; 
                            attribute :>> ordering = ObjectNodeOrderingKind::FIFO; 
                             
                        }  
                        in port 'St Cmds' : FunctionInputPort  { 
                            @CapellaID { eid = "39d47eeb-ef83-4553-abfe-75e6ec300d10"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "620ed800-5c2a-476c-9ed5-d4b86e8e3833"; } 
                            attribute :>> isControl = false; 
                            attribute :>> isControlType = false; 
                            attribute :>> kindOfNode = ObjectNodeKind::Unspecified; 
                            attribute :>> ordering = ObjectNodeOrderingKind::FIFO; 
                        }  
                         
                        ref :>> outputs =  ('eRod_Autonomous_Vehicle_2024 Project'::'eRod_Autonomous_Vehicle_2024'::'Logical Architecture'::'Logical Functions'::'Root Logical Function'.'Automatic Steering'.'FOP 1'); 
                        ref :>> inputs =  ('eRod_Autonomous_Vehicle_2024 Project'::'eRod_Autonomous_Vehicle_2024'::'Logical Architecture'::'Logical Functions'::'Root Logical Function'.'Automatic Steering'.'FIP 2',
                        'eRod_Autonomous_Vehicle_2024 Project'::'eRod_Autonomous_Vehicle_2024'::'Logical Architecture'::'Logical Functions'::'Root Logical Function'.'Automatic Steering'.'St Cmds',
                        'eRod_Autonomous_Vehicle_2024 Project'::'eRod_Autonomous_Vehicle_2024'::'Logical Architecture'::'Logical Functions'::'Root Logical Function'.'Automatic Steering'.'FIP 1'); 
                    }  
                    action 'Detect road' : LogicalFunction  { 
                        @CapellaID { eid = "fa09896a-bc90-449a-abca-899be4426e0b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Capture view' : LogicalFunction  { 
                            @CapellaID { eid = "2772de8c-7270-46a2-9219-6791d4705210"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "f264d27b-fd1b-4f3b-a2aa-08fd005ae6b5"; } 
                                attribute :>> isControl = false; 
                                attribute :>> isControlType = false; 
                                attribute :>> kindOfNode = ObjectNodeKind::Unspecified; 
                                attribute :>> ordering = ObjectNodeOrderingKind::FIFO; 
                            }  
                            in port 'FIP 2' : FunctionInputPort  { 
                                @CapellaID { eid = "ea7b7cab-3964-494b-8e99-cdb1c19dde66"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "39047ee1-9a6a-42bf-9bbe-10a07e09e845"; } 
                                attribute :>> isControl = false; 
                                attribute :>> isControlType = false; 
                                attribute :>> kindOfNode = ObjectNodeKind::Unspecified; 
                                attribute :>> ordering = ObjectNodeOrderingKind::FIFO; 
                                 
                            }  
                            ref :>> outputs =  ('eRod_Autonomous_Vehicle_2024 Project'::'eRod_Autonomous_Vehicle_2024'::'Logical Architecture'::'Logical Functions'::'Root Logical Function'.'Detect road'.'Capture view'.'FOP 1'); 
                            ref :>> inputs =  ('eRod_Autonomous_Vehicle_2024 Project'::'eRod_Autonomous_Vehicle_2024'::'Logical Architecture'::'Logical Functions'::'Root Logical Function'.'Detect road'.'Capture view'.'FIP 2',
                            'eRod_Autonomous_Vehicle_2024 Project'::'eRod_Autonomous_Vehicle_2024'::'Logical Architecture'::'Logical Functions'::'Root Logical Function'.'Detect road'.'Capture view'.'FIP 1'); 
                        }  
                        action 'Image fusion' : LogicalFunction  { 
                            @CapellaID { eid = "3e464393-0b8f-4cb0-be66-0deb5706c5bc"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "e1e944d9-2cb5-486c-bf98-33d4b30ead7d"; } 
                                attribute :>> isControl = false; 
                                attribute :>> isControlType = false; 
                                attribute :>> kindOfNode = ObjectNodeKind::Unspecified; 
                                attribute :>> ordering = ObjectNodeOrderingKind::FIFO; 
                            }  
                            out port 'FOP 2' : FunctionOutputPort  { 
                                @CapellaID { eid = "316423a6-1040-44f9-93f1-105dec7b6e2f"; } 
                                attribute :>> isControl = false; 
                                attribute :>> isControlType = false; 
                                attribute :>> kindOfNode = ObjectNodeKind::Unspecified; 
                                attribute :>> ordering = ObjectNodeOrderingKind::FIFO; 
                            }  
                            out port 'FOP 3' : FunctionOutputPort  { 
                                @CapellaID { eid = "1fe85aef-0d2e-41a2-9771-e9b01cda1f64"; } 
                                attribute :>> isControl = false; 
                                attribute :>> isControlType = false; 
                                attribute :>> kindOfNode = ObjectNodeKind::Unspecified; 
                                attribute :>> ordering = ObjectNodeOrderingKind::FIFO; 
                            }  
                            out port 'FOP 4' : FunctionOutputPort  { 
                                @CapellaID { eid = "a43c4b42-aadf-4d94-ba93-6f8ff03b14c9"; } 
                                attribute :>> isControl = false; 
                                attribute :>> isControlType = false; 
                                attribute :>> kindOfNode = ObjectNodeKind::Unspecified; 
                                attribute :>> ordering = ObjectNodeOrderingKind::FIFO; 
                            }  
                            out port 'FOP 5' : FunctionOutputPort  { 
                                @CapellaID { eid = "8489c850-0859-4492-b069-9d937a20b696"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "8c83c6ae-4f51-43f6-9b98-e1e69747c3bd"; } 
                                attribute :>> isControl = false; 
                                attribute :>> isControlType = false; 
                                attribute :>> kindOfNode = ObjectNodeKind::Unspecified; 
                                attribute :>> ordering = ObjectNodeOrderingKind::FIFO; 
                            }  
                            in port 'FIP 2' : FunctionInputPort  { 
                                @CapellaID { eid = "adc09602-fe94-4d23-ab2e-fb9c25530bc3"; } 
                                attribute :>> isControl = false; 
                                attribute :>> isControlType = false; 
                                attribute :>> kindOfNode = ObjectNodeKind::Unspecified; 
                                attribute :>> ordering = ObjectNodeOrderingKind::FIFO; 
                            }  
                            in port 'FIP 3' : FunctionInputPort  { 
                                @CapellaID { eid = "c3d45ff4-cb5c-4179-a729-92ffb7bb098b"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'Logical Architecture'::'Logical Functions'::'Root Logical Function'.'Detect road'.'Image fusion'.'FOP 1',
                            'eRod_Autonomous_Vehicle_2024 Project'::'eRod_Autonomous_Vehicle_2024'::'Logical Architecture'::'Logical Functions'::'Root Logical Function'.'Detect road'.'Image fusion'.'FOP 2',
                            'eRod_Autonomous_Vehicle_2024 Project'::'eRod_Autonomous_Vehicle_2024'::'Logical Architecture'::'Logical Functions'::'Root Logical Function'.'Detect road'.'Image fusion'.'FOP 3',
                            'eRod_Autonomous_Vehicle_2024 Project'::'eRod_Autonomous_Vehicle_2024'::'Logical Architecture'::'Logical Functions'::'Root Logical Function'.'Detect road'.'Image fusion'.'FOP 4',
                            'eRod_Autonomous_Vehicle_2024 Project'::'eRod_Autonomous_Vehicle_2024'::'Logical Architecture'::'Logical Functions'::'Root Logical Function'.'Detect road'.'Image fusion'.'FOP 5'); 
                            ref :>> inputs =  ('eRod_Autonomous_Vehicle_2024 Project'::'eRod_Autonomous_Vehicle_2024'::'Logical Architecture'::'Logical Functions'::'Root Logical Function'.'Detect road'.'Image fusion'.'FIP 1',
                            'eRod_Autonomous_Vehicle_2024 Project'::'eRod_Autonomous_Vehicle_2024'::'Logical Architecture'::'Logical Functions'::'Root Logical Function'.'Detect road'.'Image fusion'.'FIP 2',
                            'eRod_Autonomous_Vehicle_2024 Project'::'eRod_Autonomous_Vehicle_2024'::'Logical Architecture'::'Logical Functions'::'Root Logical Function'.'Detect road'.'Image fusion'.'FIP 3'); 
                        }  
                        action 'Detect path' : LogicalFunction  { 
                            @CapellaID { eid = "155641ab-e226-409f-85d3-1c7c58424f1c"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "6a89a860-5409-4a3d-a477-0d65f278804c"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "cad8e6b6-a92e-4dfb-a583-2b1ea512503d"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'Logical Architecture'::'Logical Functions'::'Root Logical Function'.'Detect road'.'Detect path'.'FOP 1'); 
                            ref :>> inputs =  ('eRod_Autonomous_Vehicle_2024 Project'::'eRod_Autonomous_Vehicle_2024'::'Logical Architecture'::'Logical Functions'::'Root Logical Function'.'Detect road'.'Detect path'.'FIP 1'); 
                        }  
                        interface '9f74537d-58c1-4d86-8f5d-62cee58197d3' : FunctionalExchange 
                            connect source ::> 'eRod_Autonomous_Vehicle_2024 Project'::'eRod_Autonomous_Vehicle_2024'::'Logical Architecture'::'Logical Functions'::'Root Logical Function'.'Detect road'.'Capture view'.'FOP 1'
                            to target ::> 'eRod_Autonomous_Vehicle_2024 Project'::'eRod_Autonomous_Vehicle_2024'::'Logical Architecture'::'Logical Functions'::'Root Logical Function'.'Detect road'.'Image fusion'.'FIP 1' { 
                            @CapellaID { eid = "9f74537d-58c1-4d86-8f5d-62cee58197d3"; } 
                            attribute :>> isMulticast = false; 
                            attribute :>> isMultireceive = false; 
                            attribute :>> kindOfRate = RateKind::Unspecified; 
                            attribute :>> interfaceName = "Video stream"; 
                        }  
                         
                        ref :>> ownedFunctions =  ('eRod_Autonomous_Vehicle_2024 Project'::'eRod_Autonomous_Vehicle_2024'::'Logical Architecture'::'Logical Functions'::'Root Logical Function'.'Detect road'.'Capture view',
                        'eRod_Autonomous_Vehicle_2024 Project'::'eRod_Autonomous_Vehicle_2024'::'Logical Architecture'::'Logical Functions'::'Root Logical Function'.'Detect road'.'Image fusion',
                        'eRod_Autonomous_Vehicle_2024 Project'::'eRod_Autonomous_Vehicle_2024'::'Logical Architecture'::'Logical Functions'::'Root Logical Function'.'Detect road'.'Detect path'); 
                        ref :>> ownedFunctionalExchanges =  ('eRod_Autonomous_Vehicle_2024 Project'::'eRod_Autonomous_Vehicle_2024'::'Logical Architecture'::'Logical Functions'::'Root Logical Function'.'Detect road'.'9f74537d-58c1-4d86-8f5d-62cee58197d3'); 
                    }  
                    action 'Provide road markers' : LogicalFunction  { 
                        @CapellaID { eid = "0c399761-05d1-42ff-8e66-4e0db7a44a81"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "4a86a992-0fcd-4e9c-956c-82ff19ddd0ee"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Provide road markers'.'FOP 1'); 
                    }  
                    action 'Provide target vehicle velocity' : LogicalFunction  { 
                        @CapellaID { eid = "6e7084c3-f8a8-4d4e-a366-6cd39f65b642"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "04988749-c34e-4abd-9e47-794e0946942a"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "1974ae52-1a15-4eb4-afc4-e6bc966a38de"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Provide target vehicle velocity'.'FOP 1',
                        'eRod_Autonomous_Vehicle_2024 Project'::'eRod_Autonomous_Vehicle_2024'::'Logical Architecture'::'Logical Functions'::'Root Logical Function'.'Provide target vehicle velocity'.'FOP 2'); 
                    }  
                    action 'Provide diverse terrain' : LogicalFunction  { 
                        @CapellaID { eid = "7596492a-3279-47ac-8798-ae7570fcf086"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outTerrain' : FunctionOutputPort  { 
                            @CapellaID { eid = "f0192f0f-cbf2-43bb-b2ff-c3095dbe6ca2"; } 
                            attribute :>> isControl = false; 
                            attribute :>> isControlType = false; 
                            attribute :>> kindOfNode = ObjectNodeKind::Unspecified; 
                            attribute :>> ordering = ObjectNodeOrderingKind::FIFO; 
                             
                        }  
                        in port 'inWeather' : FunctionInputPort  { 
                            @CapellaID { eid = "515dc840-0e27-46b1-813a-754196135c27"; } 
                            attribute :>> isControl = false; 
                            attribute :>> isControlType = false; 
                            attribute :>> kindOfNode = ObjectNodeKind::Unspecified; 
                            attribute :>> ordering = ObjectNodeOrderingKind::FIFO; 
                             
                        }  
                        in port 'inLocation' : FunctionInputPort  { 
                            @CapellaID { eid = "83bedcc3-9d53-4312-99ce-c08f5a3badc3"; } 
                            attribute :>> isControl = false; 
                            attribute :>> isControlType = false; 
                            attribute :>> kindOfNode = ObjectNodeKind::Unspecified; 
                            attribute :>> ordering = ObjectNodeOrderingKind::FIFO; 
                             
                        }  
                        in port 'inTraction' : FunctionInputPort  { 
                            @CapellaID { eid = "00d521c1-4a59-4508-a44d-df88bea0b6fd"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Provide diverse terrain'.'outTerrain'); 
                        ref :>> inputs =  ('eRod_Autonomous_Vehicle_2024 Project'::'eRod_Autonomous_Vehicle_2024'::'Logical Architecture'::'Logical Functions'::'Root Logical Function'.'Provide diverse terrain'.'inWeather',
                        'eRod_Autonomous_Vehicle_2024 Project'::'eRod_Autonomous_Vehicle_2024'::'Logical Architecture'::'Logical Functions'::'Root Logical Function'.'Provide diverse terrain'.'inLocation',
                        'eRod_Autonomous_Vehicle_2024 Project'::'eRod_Autonomous_Vehicle_2024'::'Logical Architecture'::'Logical Functions'::'Root Logical Function'.'Provide diverse terrain'.'inTraction'); 
                    }  
                    action 'Provide parking location' : LogicalFunction  { 
                        @CapellaID { eid = "246b2187-32b8-423d-8dc9-bfebb4db0523"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                         
                    }  
                    action 'Steer Wheels Remote' : LogicalFunction  { 
                        @CapellaID { eid = "6d86caa9-7c09-493a-a05f-0e8aa59c9e9c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outWheel Position' : FunctionOutputPort  { 
                            @CapellaID { eid = "47361eb2-d970-4dfc-a880-0995bafbc514"; } 
                            attribute :>> isControl = false; 
                            attribute :>> isControlType = false; 
                            attribute :>> kindOfNode = ObjectNodeKind::Unspecified; 
                            attribute :>> ordering = ObjectNodeOrderingKind::FIFO; 
                             
                        }  
                        in port 'inSteering Commands' : FunctionInputPort  { 
                            @CapellaID { eid = "f0a861c5-f6d0-4dcb-8a71-2ea77623bc33"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Steer Wheels Remote'.'outWheel Position'); 
                        ref :>> inputs =  ('eRod_Autonomous_Vehicle_2024 Project'::'eRod_Autonomous_Vehicle_2024'::'Logical Architecture'::'Logical Functions'::'Root Logical Function'.'Steer Wheels Remote'.'inSteering Commands'); 
                    }  
                    action 'Provide weather' : LogicalFunction  { 
                        @CapellaID { eid = "a0770b8a-1d17-4ce7-a96d-81e7b751bc74"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outWeather' : FunctionOutputPort  { 
                            @CapellaID { eid = "ef270295-203d-4a57-8fd0-d53ad9677125"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Provide weather'.'outWeather'); 
                    }  
                    action 'Move objects' : LogicalFunction  { 
                        @CapellaID { eid = "703d2510-6b66-4190-8387-e5dccbafbdce"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outObjects' : FunctionOutputPort  { 
                            @CapellaID { eid = "1a77934b-7bb2-470c-bbf5-ebb684a6dc16"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Move objects'.'outObjects'); 
                    }  
                    action 'Reflect light' : LogicalFunction  { 
                        @CapellaID { eid = "066357e1-ef5b-42ba-b7ee-2dd4a986b533"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "462c1d97-2922-4a34-b215-637976135b61"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'Logical Architecture'::'Logical Functions'::'Root Logical Function'.'Reflect light'.'FOP 1'); 
                    }  
                    action 'Resist Front Wheels' : LogicalFunction  { 
                        @CapellaID { eid = "b6a5921a-be84-4f19-9242-0838da869d1c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "22391811-29a0-4707-bdfe-8b947a26be51"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Logical Architecture'::'Logical Functions'::'Root Logical Function'.'Resist Front Wheels'.'FIP 1'); 
                    }  
                    action 'Park vehicle' : LogicalFunction  { 
                        @CapellaID { eid = "b3d09850-9099-46b8-a4d4-da7d2652a9e7"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outBraking Commands' : FunctionOutputPort  { 
                            @CapellaID { eid = "13701307-dc64-4f5e-ab84-9cf12e599a27"; } 
                            attribute :>> isControl = false; 
                            attribute :>> isControlType = false; 
                            attribute :>> kindOfNode = ObjectNodeKind::Unspecified; 
                            attribute :>> ordering = ObjectNodeOrderingKind::FIFO; 
                             
                        }  
                        out port 'outSteering Commands' : FunctionOutputPort  { 
                            @CapellaID { eid = "b49a5ab6-80f8-48fd-8dc4-9e55a412c55c"; } 
                            attribute :>> isControl = false; 
                            attribute :>> isControlType = false; 
                            attribute :>> kindOfNode = ObjectNodeKind::Unspecified; 
                            attribute :>> ordering = ObjectNodeOrderingKind::FIFO; 
                             
                        }  
                        in port 'inRequest parking' : FunctionInputPort  { 
                            @CapellaID { eid = "2c758bf1-2f7b-4542-8b7f-bb1f507b7562"; } 
                            attribute :>> isControl = false; 
                            attribute :>> isControlType = false; 
                            attribute :>> kindOfNode = ObjectNodeKind::Unspecified; 
                            attribute :>> ordering = ObjectNodeOrderingKind::FIFO; 
                             
                        }  
                        in port 'inInitiate Park' : FunctionInputPort  { 
                            @CapellaID { eid = "aab5fc50-a553-4802-b9ae-e0501258100c"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Park vehicle'.'outBraking Commands',
                        'eRod_Autonomous_Vehicle_2024 Project'::'eRod_Autonomous_Vehicle_2024'::'Logical Architecture'::'Logical Functions'::'Root Logical Function'.'Park vehicle'.'outSteering Commands'); 
                        ref :>> inputs =  ('eRod_Autonomous_Vehicle_2024 Project'::'eRod_Autonomous_Vehicle_2024'::'Logical Architecture'::'Logical Functions'::'Root Logical Function'.'Park vehicle'.'inRequest parking',
                        'eRod_Autonomous_Vehicle_2024 Project'::'eRod_Autonomous_Vehicle_2024'::'Logical Architecture'::'Logical Functions'::'Root Logical Function'.'Park vehicle'.'inInitiate Park'); 
                    }  
                    action 'Vehicle Command' : LogicalFunction  { 
                        @CapellaID { eid = "7cfd652d-5842-47b3-a12e-0e2bc65148b2"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outVehicle Commands' : FunctionOutputPort  { 
                            @CapellaID { eid = "a7ebf8f3-810b-4c30-853a-1628b423a253"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Vehicle Command'.'outVehicle Commands'); 
                    }  
                    action 'Receive Status of Progess ' : LogicalFunction  { 
                        @CapellaID { eid = "216c1761-9824-47e7-8de0-335c092dbeed"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'inParking Status' : FunctionInputPort  { 
                            @CapellaID { eid = "0f597d82-cc20-4dd1-bf4a-a3183fc71964"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Logical Architecture'::'Logical Functions'::'Root Logical Function'.'Receive Status of Progess '.'inParking Status'); 
                    }  
                    action 'Activate Park Assist' : LogicalFunction  { 
                        @CapellaID { eid = "fa4e257f-0f38-412c-abb0-17953f681162"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outActivate' : FunctionOutputPort  { 
                            @CapellaID { eid = "abeb0dc7-c782-430b-a09f-7d4de0bdf5e3"; } 
                            attribute :>> isControl = false; 
                            attribute :>> isControlType = false; 
                            attribute :>> kindOfNode = ObjectNodeKind::Unspecified; 
                            attribute :>> ordering = ObjectNodeOrderingKind::FIFO; 
                             
                        }  
                        out port 'outDeactivate' : FunctionOutputPort  { 
                            @CapellaID { eid = "5efc9cb6-005c-4b48-8405-0e1eb164671d"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Activate Park Assist'.'outActivate',
                        'eRod_Autonomous_Vehicle_2024 Project'::'eRod_Autonomous_Vehicle_2024'::'Logical Architecture'::'Logical Functions'::'Root Logical Function'.'Activate Park Assist'.'outDeactivate'); 
                    }  
                    action 'Status and command indication' : LogicalFunction  { 
                        @CapellaID { eid = "c6161f41-9232-40d4-9b7e-5f8cd29c5753"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outRequest parking' : FunctionOutputPort  { 
                            @CapellaID { eid = "bf40614a-fe2f-411a-82d5-f200121cdc7a"; } 
                            attribute :>> isControl = false; 
                            attribute :>> isControlType = false; 
                            attribute :>> kindOfNode = ObjectNodeKind::Unspecified; 
                            attribute :>> ordering = ObjectNodeOrderingKind::FIFO; 
                             
                        }  
                        out port 'outParking Status' : FunctionOutputPort  { 
                            @CapellaID { eid = "6c938f09-9bb8-4b80-82d9-4dc2635cc6aa"; } 
                            attribute :>> isControl = false; 
                            attribute :>> isControlType = false; 
                            attribute :>> kindOfNode = ObjectNodeKind::Unspecified; 
                            attribute :>> ordering = ObjectNodeOrderingKind::FIFO; 
                             
                        }  
                        in port 'inActivate' : FunctionInputPort  { 
                            @CapellaID { eid = "ab9edcb5-0af6-4f46-8ba7-16daa0a57b1c"; } 
                            attribute :>> isControl = false; 
                            attribute :>> isControlType = false; 
                            attribute :>> kindOfNode = ObjectNodeKind::Unspecified; 
                            attribute :>> ordering = ObjectNodeOrderingKind::FIFO; 
                             
                        }  
                        in port 'inDeactivate' : FunctionInputPort  { 
                            @CapellaID { eid = "156bf166-90c2-4489-aa10-1a61994154c8"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Status and command indication'.'outRequest parking',
                        'eRod_Autonomous_Vehicle_2024 Project'::'eRod_Autonomous_Vehicle_2024'::'Logical Architecture'::'Logical Functions'::'Root Logical Function'.'Status and command indication'.'outParking Status'); 
                        ref :>> inputs =  ('eRod_Autonomous_Vehicle_2024 Project'::'eRod_Autonomous_Vehicle_2024'::'Logical Architecture'::'Logical Functions'::'Root Logical Function'.'Status and command indication'.'inActivate',
                        'eRod_Autonomous_Vehicle_2024 Project'::'eRod_Autonomous_Vehicle_2024'::'Logical Architecture'::'Logical Functions'::'Root Logical Function'.'Status and command indication'.'inDeactivate'); 
                    }  
                    action 'Remote Operate Car' : LogicalFunction  { 
                        @CapellaID { eid = "96b598da-d74e-4f3e-b38e-91bf391e7cbe"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outInitiate Park' : FunctionOutputPort  { 
                            @CapellaID { eid = "adbb0aa5-2597-416a-a20c-e90d600a502f"; } 
                            attribute :>> isControl = false; 
                            attribute :>> isControlType = false; 
                            attribute :>> kindOfNode = ObjectNodeKind::Unspecified; 
                            attribute :>> ordering = ObjectNodeOrderingKind::FIFO; 
                             
                        }  
                        in port 'inVehicle Commands' : FunctionInputPort  { 
                            @CapellaID { eid = "3bcff247-0281-470a-a68a-2f401a2019e8"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Logical Architecture'::'Logical Functions'::'Root Logical Function'.'Remote Operate Car'.'outInitiate Park'); 
                        ref :>> inputs =  ('eRod_Autonomous_Vehicle_2024 Project'::'eRod_Autonomous_Vehicle_2024'::'Logical Architecture'::'Logical Functions'::'Root Logical Function'.'Remote Operate Car'.'inVehicle Commands'); 
                    }  
                    action 'Automatic Steer' : LogicalFunction  { 
                        @CapellaID { eid = "8c74cae6-7b3c-41ca-a51b-e0fb50f73a3b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "60e568f0-4868-41ab-a23a-cf67c4a6b1ea"; } 
                            attribute :>> isControl = false; 
                            attribute :>> isControlType = false; 
                            attribute :>> kindOfNode = ObjectNodeKind::Unspecified; 
                            attribute :>> ordering = ObjectNodeOrderingKind::FIFO; 
                        }  
                        ref :>> outputs =  ('eRod_Autonomous_Vehicle_2024 Project'::'eRod_Autonomous_Vehicle_2024'::'Logical Architecture'::'Logical Functions'::'Root Logical Function'.'Automatic Steer'.'FOP 1'); 
                    }  
                    action 'Control Accel' : LogicalFunction  { 
                        @CapellaID { eid = "6f1da64b-5ae4-42f3-b4c9-f2db297db63b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "0f1aeef7-f419-46e8-8eba-4d939208b3a1"; } 
                            attribute :>> isControl = false; 
                            attribute :>> isControlType = false; 
                            attribute :>> kindOfNode = ObjectNodeKind::Unspecified; 
                            attribute :>> ordering = ObjectNodeOrderingKind::FIFO; 
                        }  
                        in port 'inBraking Commands' : FunctionInputPort  { 
                            @CapellaID { eid = "586323b3-5fcd-4bdb-af57-5036b874b42f"; } 
                            attribute :>> isControl = false; 
                            attribute :>> isControlType = false; 
                            attribute :>> kindOfNode = ObjectNodeKind::Unspecified; 
                            attribute :>> ordering = ObjectNodeOrderingKind::FIFO; 
                             
                        }  
                        ref :>> outputs =  ('eRod_Autonomous_Vehicle_2024 Project'::'eRod_Autonomous_Vehicle_2024'::'Logical Architecture'::'Logical Functions'::'Root Logical Function'.'Control Accel'.'FOP 1'); 
                        ref :>> inputs =  ('eRod_Autonomous_Vehicle_2024 Project'::'eRod_Autonomous_Vehicle_2024'::'Logical Architecture'::'Logical Functions'::'Root Logical Function'.'Control Accel'.'inBraking Commands'); 
                    }  
                    action 'Calculate Driving Path' : LogicalFunction  { 
                        @CapellaID { eid = "4212ffec-9f63-4087-a5d2-c475bb6b61bc"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Display State of Park' : LogicalFunction  { 
                        @CapellaID { eid = "5e8ba012-b9f2-47ec-9823-be1b5dbad348"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    interface 'b953457a-88f3-40b9-a380-8bbaeb6110c8' : FunctionalExchange 
                        connect source ::> 'eRod_Autonomous_Vehicle_2024 Project'::'eRod_Autonomous_Vehicle_2024'::'Logical Architecture'::'Logical Functions'::'Root Logical Function'.'Stop'.'outProvide'
                        to target ::> 'eRod_Autonomous_Vehicle_2024 Project'::'eRod_Autonomous_Vehicle_2024'::'Logical Architecture'::'Logical Functions'::'Root Logical Function'.'Car racing experience absorbed'.'inProvide' { 
                        @CapellaID { eid = "b953457a-88f3-40b9-a380-8bbaeb6110c8"; } 
                        attribute :>> isMulticast = false; 
                        attribute :>> isMultireceive = false; 
                        attribute :>> kindOfRate = RateKind::Unspecified; 
                        attribute :>> interfaceName = "Cause"; 
                         
                    }  
                    interface '49b41474-6068-48af-9f20-48587c061248' : FunctionalExchange 
                        connect source ::> 'eRod_Autonomous_Vehicle_2024 Project'::'eRod_Autonomous_Vehicle_2024'::'Logical Architecture'::'Logical Functions'::'Root Logical Function'.'Motor overheating warning '.'outDisplay'
                        to target ::> 'eRod_Autonomous_Vehicle_2024 Project'::'eRod_Autonomous_Vehicle_2024'::'Logical Architecture'::'Logical Functions'::'Root Logical Function'.'Get informed with issues'.'inDisplay' { 
                        @CapellaID { eid = "49b41474-6068-48af-9f20-48587c061248"; } 
                        attribute :>> isMulticast = false; 
                        attribute :>> isMultireceive = false; 
                        attribute :>> kindOfRate = RateKind::Unspecified; 
                        attribute :>> interfaceName = "Display"; 
                         
                    }  
                    interface '37640148-3029-4dd4-98be-abe69563435f' : FunctionalExchange 
                        connect source ::> 'eRod_Autonomous_Vehicle_2024 Project'::'eRod_Autonomous_Vehicle_2024'::'Logical Architecture'::'Logical Functions'::'Root Logical Function'.'Motor Start'.'outCause'
                        to target ::> 'eRod_Autonomous_Vehicle_2024 Project'::'eRod_Autonomous_Vehicle_2024'::'Logical Architecture'::'Logical Functions'::'Root Logical Function'.'Transfer Energy'.'Acquire electrical Energy'.'FIP 1' { 
                        @CapellaID { eid = "37640148-3029-4dd4-98be-abe69563435f"; } 
                        attribute :>> isMulticast = false; 
                        attribute :>> isMultireceive = false; 
                        attribute :>> kindOfRate = RateKind::Unspecified; 
                        attribute :>> interfaceName = "Signal"; 
                         
                    }  
                    interface '0e825f29-7978-4cea-92bf-ed5a75495285' : FunctionalExchange 
                        connect source ::> 'eRod_Autonomous_Vehicle_2024 Project'::'eRod_Autonomous_Vehicle_2024'::'Logical Architecture'::'Logical Functions'::'Root Logical Function'.'Get informed with issues'.'FOP 1'
                        to target ::> 'eRod_Autonomous_Vehicle_2024 Project'::'eRod_Autonomous_Vehicle_2024'::'Logical Architecture'::'Logical Functions'::'Root Logical Function'.'Report issues'.'FIP 1' { 
                        @CapellaID { eid = "0e825f29-7978-4cea-92bf-ed5a75495285"; } 
                        attribute :>> isMulticast = false; 
                        attribute :>> isMultireceive = false; 
                        attribute :>> kindOfRate = RateKind::Unspecified; 
                        attribute :>> interfaceName = "action"; 
                         
                    }  
                    interface 'd83bfe14-3bb0-443f-8b64-ac175f2b9aa1' : FunctionalExchange 
                        connect source ::> 'eRod_Autonomous_Vehicle_2024 Project'::'eRod_Autonomous_Vehicle_2024'::'Logical Architecture'::'Logical Functions'::'Root Logical Function'.'Drive on a race track'.'outCommand'
                        to target ::> 'eRod_Autonomous_Vehicle_2024 Project'::'eRod_Autonomous_Vehicle_2024'::'Logical Architecture'::'Logical Functions'::'Root Logical Function'.'Motor Start'.'FIP 2' { 
                        @CapellaID { eid = "d83bfe14-3bb0-443f-8b64-ac175f2b9aa1"; } 
                        attribute :>> isMulticast = false; 
                        attribute :>> isMultireceive = false; 
                        attribute :>> kindOfRate = RateKind::Unspecified; 
                        attribute :>> interfaceName = "Command"; 
                         
                    }  
                    interface '76b26dd2-2a46-4b84-b303-1c3132586ce4' : FunctionalExchange 
                        connect source ::> 'eRod_Autonomous_Vehicle_2024 Project'::'eRod_Autonomous_Vehicle_2024'::'Logical Architecture'::'Logical Functions'::'Root Logical Function'.'Motor protect'.'Detect temperature limit'.'FOP 3'
                        to target ::> 'eRod_Autonomous_Vehicle_2024 Project'::'eRod_Autonomous_Vehicle_2024'::'Logical Architecture'::'Logical Functions'::'Root Logical Function'.'Motor overheating warning '.'inCause' { 
                        @CapellaID { eid = "76b26dd2-2a46-4b84-b303-1c3132586ce4"; } 
                        attribute :>> isMulticast = false; 
                        attribute :>> isMultireceive = false; 
                        attribute :>> kindOfRate = RateKind::Unspecified; 
                        attribute :>> interfaceName = "Display signal"; 
                         
                    }  
                    interface '8284c472-1721-460b-a37b-cf61ee2657b7' : FunctionalExchange 
                        connect source ::> 'eRod_Autonomous_Vehicle_2024 Project'::'eRod_Autonomous_Vehicle_2024'::'Logical Architecture'::'Logical Functions'::'Root Logical Function'.'Transfer heat'.'Reduce power'.'FOP 1'
                        to target ::> 'eRod_Autonomous_Vehicle_2024 Project'::'eRod_Autonomous_Vehicle_2024'::'Logical Architecture'::'Logical Functions'::'Root Logical Function'.'Deaccelerate'.'FIP 1' { 
                        @CapellaID { eid = "8284c472-1721-460b-a37b-cf61ee2657b7"; } 
                        attribute :>> isMulticast = false; 
                        attribute :>> isMultireceive = false; 
                        attribute :>> kindOfRate = RateKind::Unspecified; 
                        attribute :>> interfaceName = "Power"; 
                         
                    }  
                    interface '89d97516-8ef5-40a7-98d5-18282eaded97' : FunctionalExchange 
                        connect source ::> 'eRod_Autonomous_Vehicle_2024 Project'::'eRod_Autonomous_Vehicle_2024'::'Logical Architecture'::'Logical Functions'::'Root Logical Function'.'Deaccelerate'.'FOP 1'
                        to target ::> 'eRod_Autonomous_Vehicle_2024 Project'::'eRod_Autonomous_Vehicle_2024'::'Logical Architecture'::'Logical Functions'::'Root Logical Function'.'Stop'.'FIP 1' { 
                        @CapellaID { eid = "89d97516-8ef5-40a7-98d5-18282eaded97"; } 
                        attribute :>> isMulticast = false; 
                        attribute :>> isMultireceive = false; 
                        attribute :>> kindOfRate = RateKind::Unspecified; 
                        attribute :>> interfaceName = "Energy"; 
                         
                    }  
                    interface '61aa0363-0061-464c-bc92-e50e39909e33' : FunctionalExchange 
                        connect source ::> 'eRod_Autonomous_Vehicle_2024 Project'::'eRod_Autonomous_Vehicle_2024'::'Logical Architecture'::'Logical Functions'::'Root Logical Function'.'Report issues'.'FOP 1'
                        to target ::> 'eRod_Autonomous_Vehicle_2024 Project'::'eRod_Autonomous_Vehicle_2024'::'Logical Architecture'::'Logical Functions'::'Root Logical Function'.'Software update'.'inFeedback' { 
                        @CapellaID { eid = "61aa0363-0061-464c-bc92-e50e39909e33"; } 
                        attribute :>> isMulticast = false; 
                        attribute :>> isMultireceive = false; 
                        attribute :>> kindOfRate = RateKind::Unspecified; 
                        attribute :>> interfaceName = "Information"; 
                         
                    }  
                    interface '8db9677b-6d28-4860-959e-3ee1b2019e3b' : FunctionalExchange 
                        connect source ::> 'eRod_Autonomous_Vehicle_2024 Project'::'eRod_Autonomous_Vehicle_2024'::'Logical Architecture'::'Logical Functions'::'Root Logical Function'.'Get Software-update'.'FOP 1'
                        to target ::> 'eRod_Autonomous_Vehicle_2024 Project'::'eRod_Autonomous_Vehicle_2024'::'Logical Architecture'::'Logical Functions'::'Root Logical Function'.'Software update'.'inFeedback' { 
                        @CapellaID { eid = "8db9677b-6d28-4860-959e-3ee1b2019e3b"; } 
                        attribute :>> isMulticast = false; 
                        attribute :>> isMultireceive = false; 
                        attribute :>> kindOfRate = RateKind::Unspecified; 
                        attribute :>> interfaceName = "enable"; 
                    }  
                    interface '74867a97-5a2c-491c-9dce-59691e217f48' : FunctionalExchange 
                        connect source ::> 'eRod_Autonomous_Vehicle_2024 Project'::'eRod_Autonomous_Vehicle_2024'::'Logical Architecture'::'Logical Functions'::'Root Logical Function'.'Software update'.'outRe-enable'
                        to target ::> 'eRod_Autonomous_Vehicle_2024 Project'::'eRod_Autonomous_Vehicle_2024'::'Logical Architecture'::'Logical Functions'::'Root Logical Function'.'Control temperature'.'Limit temperature'.'FIP 1' { 
                        @CapellaID { eid = "74867a97-5a2c-491c-9dce-59691e217f48"; } 
                        attribute :>> isMulticast = false; 
                        attribute :>> isMultireceive = false; 
                        attribute :>> kindOfRate = RateKind::Unspecified; 
                        attribute :>> interfaceName = "signal"; 
                         
                    }  
                    interface 'd697c6f7-0d8d-4400-9831-689058aece59' : FunctionalExchange 
                        connect source ::> 'eRod_Autonomous_Vehicle_2024 Project'::'eRod_Autonomous_Vehicle_2024'::'Logical Architecture'::'Logical Functions'::'Root Logical Function'.'Apply rotation on wheels'.'FOP 1'
                        to target ::> 'eRod_Autonomous_Vehicle_2024 Project'::'eRod_Autonomous_Vehicle_2024'::'Logical Architecture'::'Logical Functions'::'Root Logical Function'.'Control temperature'.'Limit power'.'FIP 3' { 
                        @CapellaID { eid = "d697c6f7-0d8d-4400-9831-689058aece59"; } 
                        attribute :>> isMulticast = false; 
                        attribute :>> isMultireceive = false; 
                        attribute :>> kindOfRate = RateKind::Unspecified; 
                        attribute :>> interfaceName = "Power"; 
                         
                    }  
                    interface '6ac2dbe1-37d1-40d6-b342-7544db1c549d' : FunctionalExchange 
                        connect source ::> 'eRod_Autonomous_Vehicle_2024 Project'::'eRod_Autonomous_Vehicle_2024'::'Logical Architecture'::'Logical Functions'::'Root Logical Function'.'Transfer Energy'.'Generate heat'.'FOP 1'
                        to target ::> 'eRod_Autonomous_Vehicle_2024 Project'::'eRod_Autonomous_Vehicle_2024'::'Logical Architecture'::'Logical Functions'::'Root Logical Function'.'Transfer heat'.'Monitor temperature'.'FIP 1' { 
                        @CapellaID { eid = "6ac2dbe1-37d1-40d6-b342-7544db1c549d"; } 
                        attribute :>> isMulticast = false; 
                        attribute :>> isMultireceive = false; 
                        attribute :>> kindOfRate = RateKind::Unspecified; 
                        attribute :>> interfaceName = "Heat flow"; 
                         
                    }  
                    interface '3b2fa504-9f86-4fba-8878-a557fb2e37c6' : FunctionalExchange 
                        connect source ::> 'eRod_Autonomous_Vehicle_2024 Project'::'eRod_Autonomous_Vehicle_2024'::'Logical Architecture'::'Logical Functions'::'Root Logical Function'.'Control temperature'.'Limit power'.'FOP 1'
                        to target ::> 'eRod_Autonomous_Vehicle_2024 Project'::'eRod_Autonomous_Vehicle_2024'::'Logical Architecture'::'Logical Functions'::'Root Logical Function'.'deliver mechanical power'.'FIP 3' { 
                        @CapellaID { eid = "3b2fa504-9f86-4fba-8878-a557fb2e37c6"; } 
                        attribute :>> isMulticast = false; 
                        attribute :>> isMultireceive = false; 
                        attribute :>> kindOfRate = RateKind::Unspecified; 
                        attribute :>> interfaceName = "Power"; 
                         
                    }  
                    interface 'c151213d-abcb-4610-894b-50fcd89715b0' : FunctionalExchange 
                        connect source ::> 'eRod_Autonomous_Vehicle_2024 Project'::'eRod_Autonomous_Vehicle_2024'::'Logical Architecture'::'Logical Functions'::'Root Logical Function'.'Sporty drive'.'FOP 2'
                        to target ::> 'eRod_Autonomous_Vehicle_2024 Project'::'eRod_Autonomous_Vehicle_2024'::'Logical Architecture'::'Logical Functions'::'Root Logical Function'.'Obtain car racing experience'.'FIP 1' { 
                        @CapellaID { eid = "c151213d-abcb-4610-894b-50fcd89715b0"; } 
                        attribute :>> isMulticast = false; 
                        attribute :>> isMultireceive = false; 
                        attribute :>> kindOfRate = RateKind::Unspecified; 
                        attribute :>> interfaceName = "Experience"; 
                         
                    }  
                    interface 'a4b7ed98-d219-4ab0-afad-a46848adc7ad' : FunctionalExchange 
                        connect source ::> 'eRod_Autonomous_Vehicle_2024 Project'::'eRod_Autonomous_Vehicle_2024'::'Logical Architecture'::'Logical Functions'::'Root Logical Function'.'Transfer Energy'.'Acquire electrical Energy'.'FOP 1'
                        to target ::> 'eRod_Autonomous_Vehicle_2024 Project'::'eRod_Autonomous_Vehicle_2024'::'Logical Architecture'::'Logical Functions'::'Root Logical Function'.'deliver mechanical power'.'FIP 1' { 
                        @CapellaID { eid = "a4b7ed98-d219-4ab0-afad-a46848adc7ad"; } 
                        attribute :>> isMulticast = false; 
                        attribute :>> isMultireceive = false; 
                        attribute :>> kindOfRate = RateKind::Unspecified; 
                        attribute :>> interfaceName = "Electricity"; 
                         
                    }  
                    interface '285ee071-9867-4f7f-abaf-dfbfeff65f67' : FunctionalExchange 
                        connect source ::> 'eRod_Autonomous_Vehicle_2024 Project'::'eRod_Autonomous_Vehicle_2024'::'Logical Architecture'::'Logical Functions'::'Root Logical Function'.'Transfer Energy'.'Acquire electrical Energy'.'FOP 2'
                        to target ::> 'eRod_Autonomous_Vehicle_2024 Project'::'eRod_Autonomous_Vehicle_2024'::'Logical Architecture'::'Logical Functions'::'Root Logical Function'.'Provide magnetic field'.'FIP 1' { 
                        @CapellaID { eid = "285ee071-9867-4f7f-abaf-dfbfeff65f67"; } 
                        attribute :>> isMulticast = false; 
                        attribute :>> isMultireceive = false; 
                        attribute :>> kindOfRate = RateKind::Unspecified; 
                        attribute :>> interfaceName = "Electricity"; 
                    }  
                    interface '819c5300-ab95-4dc1-875a-b233e8abdfac' : FunctionalExchange 
                        connect source ::> 'eRod_Autonomous_Vehicle_2024 Project'::'eRod_Autonomous_Vehicle_2024'::'Logical Architecture'::'Logical Functions'::'Root Logical Function'.'deliver mechanical power'.'FOP 1'
                        to target ::> 'eRod_Autonomous_Vehicle_2024 Project'::'eRod_Autonomous_Vehicle_2024'::'Logical Architecture'::'Logical Functions'::'Root Logical Function'.'Generate heat (Rotor)'.'FIP 1' { 
                        @CapellaID { eid = "819c5300-ab95-4dc1-875a-b233e8abdfac"; } 
                        attribute :>> isMulticast = false; 
                        attribute :>> isMultireceive = false; 
                        attribute :>> kindOfRate = RateKind::Unspecified; 
                        attribute :>> interfaceName = "energy losses"; 
                    }  
                    interface 'f0a7c5c5-8077-4718-bf83-a61a4cf56123' : FunctionalExchange 
                        connect source ::> 'eRod_Autonomous_Vehicle_2024 Project'::'eRod_Autonomous_Vehicle_2024'::'Logical Architecture'::'Logical Functions'::'Root Logical Function'.'Provide magnetic field'.'FOP 1'
                        to target ::> 'eRod_Autonomous_Vehicle_2024 Project'::'eRod_Autonomous_Vehicle_2024'::'Logical Architecture'::'Logical Functions'::'Root Logical Function'.'Generate Heat (Stator)'.'FIP 1' { 
                        @CapellaID { eid = "f0a7c5c5-8077-4718-bf83-a61a4cf56123"; } 
                        attribute :>> isMulticast = false; 
                        attribute :>> isMultireceive = false; 
                        attribute :>> kindOfRate = RateKind::Unspecified; 
                        attribute :>> interfaceName = "energy losses"; 
                    }  
                    interface 'fbab703c-b455-4208-af50-8fe4d4c8d693' : FunctionalExchange 
                        connect source ::> 'eRod_Autonomous_Vehicle_2024 Project'::'eRod_Autonomous_Vehicle_2024'::'Logical Architecture'::'Logical Functions'::'Root Logical Function'.'Generate heat (Rotor)'.'FOP 1'
                        to target ::> 'eRod_Autonomous_Vehicle_2024 Project'::'eRod_Autonomous_Vehicle_2024'::'Logical Architecture'::'Logical Functions'::'Root Logical Function'.'Gather 21'.'FIP 1' { 
                        @CapellaID { eid = "fbab703c-b455-4208-af50-8fe4d4c8d693"; } 
                        attribute :>> isMulticast = false; 
                        attribute :>> isMultireceive = false; 
                        attribute :>> kindOfRate = RateKind::Unspecified; 
                        attribute :>> interfaceName = "Heat flow"; 
                        ref :>> exchangedItems =  ('eRod_Autonomous_Vehicle_2024 Project'::'eRod_Autonomous_Vehicle_2024'::'Logical Architecture'::'Data'::'Heat'); 
                    }  
                    interface 'ac15c188-c849-4add-8db5-5c783d913d61' : FunctionalExchange 
                        connect source ::> 'eRod_Autonomous_Vehicle_2024 Project'::'eRod_Autonomous_Vehicle_2024'::'Logical Architecture'::'Logical Functions'::'Root Logical Function'.'Generate Heat (Stator)'.'FOP 1'
                        to target ::> 'eRod_Autonomous_Vehicle_2024 Project'::'eRod_Autonomous_Vehicle_2024'::'Logical Architecture'::'Logical Functions'::'Root Logical Function'.'Gather 21'.'FIP 2' { 
                        @CapellaID { eid = "ac15c188-c849-4add-8db5-5c783d913d61"; } 
                        attribute :>> isMulticast = false; 
                        attribute :>> isMultireceive = false; 
                        attribute :>> kindOfRate = RateKind::Unspecified; 
                        attribute :>> interfaceName = "Heat flow"; 
                        ref :>> exchangedItems =  ('eRod_Autonomous_Vehicle_2024 Project'::'eRod_Autonomous_Vehicle_2024'::'Logical Architecture'::'Data'::'Heat'); 
                    }  
                    interface '690b4231-60c3-43fd-ae81-d3f3f2d64519' : FunctionalExchange 
                        connect source ::> 'eRod_Autonomous_Vehicle_2024 Project'::'eRod_Autonomous_Vehicle_2024'::'Logical Architecture'::'Logical Functions'::'Root Logical Function'.'Transfer heat'.'FOP 1'
                        to target ::> 'eRod_Autonomous_Vehicle_2024 Project'::'eRod_Autonomous_Vehicle_2024'::'Logical Architecture'::'Logical Functions'::'Root Logical Function'.'Motor protect'.'Monitor temperature'.'FIP 1' { 
                        @CapellaID { eid = "690b4231-60c3-43fd-ae81-d3f3f2d64519"; } 
                        attribute :>> isMulticast = false; 
                        attribute :>> isMultireceive = false; 
                        attribute :>> kindOfRate = RateKind::Unspecified; 
                        attribute :>> interfaceName = "Heat flow"; 
                    }  
                    interface '3b5e8600-d938-4502-bd08-5d95e69970d5' : FunctionalExchange 
                        connect source ::> 'eRod_Autonomous_Vehicle_2024 Project'::'eRod_Autonomous_Vehicle_2024'::'Logical Architecture'::'Logical Functions'::'Root Logical Function'.'Gather 21'.'FOP 1'
                        to target ::> 'eRod_Autonomous_Vehicle_2024 Project'::'eRod_Autonomous_Vehicle_2024'::'Logical Architecture'::'Logical Functions'::'Root Logical Function'.'Transfer heat'.'FIP 1' { 
                        @CapellaID { eid = "3b5e8600-d938-4502-bd08-5d95e69970d5"; } 
                        attribute :>> isMulticast = false; 
                        attribute :>> isMultireceive = false; 
                        attribute :>> kindOfRate = RateKind::Unspecified; 
                        attribute :>> interfaceName = "Heat flow"; 
                        ref :>> exchangedItems =  ('eRod_Autonomous_Vehicle_2024 Project'::'eRod_Autonomous_Vehicle_2024'::'Logical Architecture'::'Data'::'Heat'); 
                    }  
                    interface '1cbd00ec-4044-4944-96b5-97902f698ad7' : FunctionalExchange 
                        connect source ::> 'eRod_Autonomous_Vehicle_2024 Project'::'eRod_Autonomous_Vehicle_2024'::'Logical Architecture'::'Logical Functions'::'Root Logical Function'.'deliver mechanical power'.'FOP 2'
                        to target ::> 'eRod_Autonomous_Vehicle_2024 Project'::'eRod_Autonomous_Vehicle_2024'::'Logical Architecture'::'Logical Functions'::'Root Logical Function'.'Transfer power to Axies'.'FIP 1' { 
                        @CapellaID { eid = "1cbd00ec-4044-4944-96b5-97902f698ad7"; } 
                        attribute :>> isMulticast = false; 
                        attribute :>> isMultireceive = false; 
                        attribute :>> kindOfRate = RateKind::Unspecified; 
                        attribute :>> interfaceName = "Torque"; 
                    }  
                    interface 'ad75ca27-9657-4f7a-b9f0-91f8f72375b0' : FunctionalExchange 
                        connect source ::> 'eRod_Autonomous_Vehicle_2024 Project'::'eRod_Autonomous_Vehicle_2024'::'Logical Architecture'::'Logical Functions'::'Root Logical Function'.'Transfer power to Axies'.'FOP 1'
                        to target ::> 'eRod_Autonomous_Vehicle_2024 Project'::'eRod_Autonomous_Vehicle_2024'::'Logical Architecture'::'Logical Functions'::'Root Logical Function'.'Apply rotation on wheels'.'power' { 
                        @CapellaID { eid = "ad75ca27-9657-4f7a-b9f0-91f8f72375b0"; } 
                        attribute :>> isMulticast = false; 
                        attribute :>> isMultireceive = false; 
                        attribute :>> kindOfRate = RateKind::Unspecified; 
                        attribute :>> interfaceName = "Torque"; 
                    }  
                    interface '9834ba0a-fa40-4c5c-b41c-f4eab563640f' : FunctionalExchange 
                        connect source ::> 'eRod_Autonomous_Vehicle_2024 Project'::'eRod_Autonomous_Vehicle_2024'::'Logical Architecture'::'Logical Functions'::'Root Logical Function'.'Motor protect'.'Reduce power'.'FOP 1'
                        to target ::> 'eRod_Autonomous_Vehicle_2024 Project'::'eRod_Autonomous_Vehicle_2024'::'Logical Architecture'::'Logical Functions'::'Root Logical Function'.'deliver mechanical power'.'FIP 3' { 
                        @CapellaID { eid = "9834ba0a-fa40-4c5c-b41c-f4eab563640f"; } 
                        attribute :>> isMulticast = false; 
                        attribute :>> isMultireceive = false; 
                        attribute :>> kindOfRate = RateKind::Unspecified; 
                        attribute :>> interfaceName = "Command"; 
                    }  
                    interface 'ffd7802c-2093-4298-a18f-a98778d74812' : FunctionalExchange 
                        connect source ::> 'eRod_Autonomous_Vehicle_2024 Project'::'eRod_Autonomous_Vehicle_2024'::'Logical Architecture'::'Logical Functions'::'Root Logical Function'.'Apply rotation on wheels'.'FOP 2'
                        to target ::> 'eRod_Autonomous_Vehicle_2024 Project'::'eRod_Autonomous_Vehicle_2024'::'Logical Architecture'::'Logical Functions'::'Root Logical Function'.'Split 25'.'FIP 1' { 
                        @CapellaID { eid = "ffd7802c-2093-4298-a18f-a98778d74812"; } 
                        attribute :>> isMulticast = false; 
                        attribute :>> isMultireceive = false; 
                        attribute :>> kindOfRate = RateKind::Unspecified; 
                        attribute :>> interfaceName = "power"; 
                    }  
                    interface '36b16c46-58ff-4544-a888-051ef74aa3f1' : FunctionalExchange 
                        connect source ::> 'eRod_Autonomous_Vehicle_2024 Project'::'eRod_Autonomous_Vehicle_2024'::'Logical Architecture'::'Logical Functions'::'Root Logical Function'.'Split 25'.'FOP 1'
                        to target ::> 'eRod_Autonomous_Vehicle_2024 Project'::'eRod_Autonomous_Vehicle_2024'::'Logical Architecture'::'Logical Functions'::'Root Logical Function'.'Sporty drive'.'FIP 2' { 
                        @CapellaID { eid = "36b16c46-58ff-4544-a888-051ef74aa3f1"; } 
                        attribute :>> isMulticast = false; 
                        attribute :>> isMultireceive = false; 
                        attribute :>> kindOfRate = RateKind::Unspecified; 
                        attribute :>> interfaceName = "Rotation"; 
                    }  
                    interface '19d12ee0-70a6-49d7-9468-396730331e38' : FunctionalExchange 
                        connect source ::> 'eRod_Autonomous_Vehicle_2024 Project'::'eRod_Autonomous_Vehicle_2024'::'Logical Architecture'::'Logical Functions'::'Root Logical Function'.'Split 25'.'FOP 2'
                        to target ::> 'eRod_Autonomous_Vehicle_2024 Project'::'eRod_Autonomous_Vehicle_2024'::'Logical Architecture'::'Logical Functions'::'Root Logical Function'.'Deaccelerate'.'FIP 1' { 
                        @CapellaID { eid = "19d12ee0-70a6-49d7-9468-396730331e38"; } 
                        attribute :>> isMulticast = false; 
                        attribute :>> isMultireceive = false; 
                        attribute :>> kindOfRate = RateKind::Unspecified; 
                        attribute :>> interfaceName = "Power"; 
                    }  
                    interface '1c8eb00e-609f-4b63-a76b-87c7ff537808' : FunctionalExchange 
                        connect source ::> 'eRod_Autonomous_Vehicle_2024 Project'::'eRod_Autonomous_Vehicle_2024'::'Logical Architecture'::'Logical Functions'::'Root Logical Function'.'Improve motor performance'.'FOP 1'
                        to target ::> 'eRod_Autonomous_Vehicle_2024 Project'::'eRod_Autonomous_Vehicle_2024'::'Logical Architecture'::'Logical Functions'::'Root Logical Function'.'Control temperature'.'Limit power'.'Command' { 
                        @CapellaID { eid = "1c8eb00e-609f-4b63-a76b-87c7ff537808"; } 
                        attribute :>> isMulticast = false; 
                        attribute :>> isMultireceive = false; 
                        attribute :>> kindOfRate = RateKind::Unspecified; 
                        attribute :>> interfaceName = "Command"; 
                    }  
                    interface 'd77bb122-0bf9-49c8-9349-3c2748585be1' : FunctionalExchange 
                        connect source ::> 'eRod_Autonomous_Vehicle_2024 Project'::'eRod_Autonomous_Vehicle_2024'::'Logical Architecture'::'Logical Functions'::'Root Logical Function'.'Control temperature'.'Limit power'.'FOP 2'
                        to target ::> 'eRod_Autonomous_Vehicle_2024 Project'::'eRod_Autonomous_Vehicle_2024'::'Logical Architecture'::'Logical Functions'::'Root Logical Function'.'deliver mechanical power'.'FIP 4' { 
                        @CapellaID { eid = "d77bb122-0bf9-49c8-9349-3c2748585be1"; } 
                        attribute :>> isMulticast = false; 
                        attribute :>> isMultireceive = false; 
                        attribute :>> kindOfRate = RateKind::Unspecified; 
                        attribute :>> interfaceName = "Signal"; 
                    }  
                    interface 'e8eeb1b5-4b14-436d-939f-422741f61b33' : FunctionalExchange 
                        connect source ::> 'eRod_Autonomous_Vehicle_2024 Project'::'eRod_Autonomous_Vehicle_2024'::'Logical Architecture'::'Logical Functions'::'Root Logical Function'.'Sporty drive'.'FOP 3'
                        to target ::> 'eRod_Autonomous_Vehicle_2024 Project'::'eRod_Autonomous_Vehicle_2024'::'Logical Architecture'::'Logical Functions'::'Root Logical Function'.'Obtain car racing experience'.'FIP 1' { 
                        @CapellaID { eid = "e8eeb1b5-4b14-436d-939f-422741f61b33"; } 
                        attribute :>> isMulticast = false; 
                        attribute :>> isMultireceive = false; 
                        attribute :>> kindOfRate = RateKind::Unspecified; 
                        attribute :>> interfaceName = "Experience"; 
                    }  
                    interface 'cccc8414-558e-44b8-b776-c579e6e76e24' : FunctionalExchange 
                        connect source ::> 'eRod_Autonomous_Vehicle_2024 Project'::'eRod_Autonomous_Vehicle_2024'::'Logical Architecture'::'Logical Functions'::'Root Logical Function'.'Get Software-update'.'FOP 1'
                        to target ::> 'eRod_Autonomous_Vehicle_2024 Project'::'eRod_Autonomous_Vehicle_2024'::'Logical Architecture'::'Logical Functions'::'Root Logical Function'.'Improve motor performance'.'FIP 1' { 
                        @CapellaID { eid = "cccc8414-558e-44b8-b776-c579e6e76e24"; } 
                        attribute :>> isMulticast = false; 
                        attribute :>> isMultireceive = false; 
                        attribute :>> kindOfRate = RateKind::Unspecified; 
                        attribute :>> interfaceName = "Enable"; 
                    }  
                    interface 'f99d3480-8396-4875-ab8d-a585b18c50b9' : FunctionalExchange 
                        connect source ::> 'eRod_Autonomous_Vehicle_2024 Project'::'eRod_Autonomous_Vehicle_2024'::'Logical Architecture'::'Logical Functions'::'Root Logical Function'.'Provide electrical energy'.'FOP 1'
                        to target ::> 'eRod_Autonomous_Vehicle_2024 Project'::'eRod_Autonomous_Vehicle_2024'::'Logical Architecture'::'Logical Functions'::'Root Logical Function'.'Transfer Energy'.'Acquire electrical Energy'.'FIP 3' { 
                        @CapellaID { eid = "f99d3480-8396-4875-ab8d-a585b18c50b9"; } 
                        attribute :>> isMulticast = false; 
                        attribute :>> isMultireceive = false; 
                        attribute :>> kindOfRate = RateKind::Unspecified; 
                        attribute :>> interfaceName = "Electricity"; 
                        ref :>> exchangedItems =  ('eRod_Autonomous_Vehicle_2024 Project'::'eRod_Autonomous_Vehicle_2024'::'Logical Architecture'::'Data'::'Electricity'); 
                    }  
                    interface '35f8b5be-612f-4161-9869-5ed9168530a1' : FunctionalExchange 
                        connect source ::> 'eRod_Autonomous_Vehicle_2024 Project'::'eRod_Autonomous_Vehicle_2024'::'Logical Architecture'::'Logical Functions'::'Root Logical Function'.'connected to the center'.'FOP 1'
                        to target ::> 'eRod_Autonomous_Vehicle_2024 Project'::'eRod_Autonomous_Vehicle_2024'::'Logical Architecture'::'Logical Functions'::'Root Logical Function'.'remote update'.'FIP 1' { 
                        @CapellaID { eid = "35f8b5be-612f-4161-9869-5ed9168530a1"; } 
                        attribute :>> isMulticast = false; 
                        attribute :>> isMultireceive = false; 
                        attribute :>> kindOfRate = RateKind::Unspecified; 
                        attribute :>> interfaceName = "enable"; 
                    }  
                    interface 'a12b9128-eb74-493c-9720-4f801a24d6a6' : FunctionalExchange 
                        connect source ::> 'eRod_Autonomous_Vehicle_2024 Project'::'eRod_Autonomous_Vehicle_2024'::'Logical Architecture'::'Logical Functions'::'Root Logical Function'.'Capture points'.'FOP 1'
                        to target ::> 'eRod_Autonomous_Vehicle_2024 Project'::'eRod_Autonomous_Vehicle_2024'::'Logical Architecture'::'Logical Functions'::'Root Logical Function'.'Detect road'.'Image fusion'.'FIP 2' { 
                        @CapellaID { eid = "a12b9128-eb74-493c-9720-4f801a24d6a6"; } 
                        attribute :>> isMulticast = false; 
                        attribute :>> isMultireceive = false; 
                        attribute :>> kindOfRate = RateKind::Unspecified; 
                        attribute :>> interfaceName = "Point cloud"; 
                    }  
                    interface '20d0cafd-e854-4bae-bf97-788b841ea877' : FunctionalExchange 
                        connect source ::> 'eRod_Autonomous_Vehicle_2024 Project'::'eRod_Autonomous_Vehicle_2024'::'Logical Architecture'::'Logical Functions'::'Root Logical Function'.'Capture radar echo'.'FOP 1'
                        to target ::> 'eRod_Autonomous_Vehicle_2024 Project'::'eRod_Autonomous_Vehicle_2024'::'Logical Architecture'::'Logical Functions'::'Root Logical Function'.'Detect road'.'Image fusion'.'FIP 3' { 
                        @CapellaID { eid = "20d0cafd-e854-4bae-bf97-788b841ea877"; } 
                        attribute :>> isMulticast = false; 
                        attribute :>> isMultireceive = false; 
                        attribute :>> kindOfRate = RateKind::Unspecified; 
                        attribute :>> interfaceName = "Point cloud"; 
                    }  
                    interface '0c5c6960-d5fb-4270-84e1-f3c7076e9fa6' : FunctionalExchange 
                        connect source ::> 'eRod_Autonomous_Vehicle_2024 Project'::'eRod_Autonomous_Vehicle_2024'::'Logical Architecture'::'Logical Functions'::'Root Logical Function'.'Detect road'.'Image fusion'.'FOP 1'
                        to target ::> 'eRod_Autonomous_Vehicle_2024 Project'::'eRod_Autonomous_Vehicle_2024'::'Logical Architecture'::'Logical Functions'::'Root Logical Function'.'Detect obstacles'.'FIP 1' { 
                        @CapellaID { eid = "0c5c6960-d5fb-4270-84e1-f3c7076e9fa6"; } 
                        attribute :>> isMulticast = false; 
                        attribute :>> isMultireceive = false; 
                        attribute :>> kindOfRate = RateKind::Unspecified; 
                        attribute :>> interfaceName = "Image data"; 
                    }  
                    interface '362d23cd-3e2a-4128-8134-4de34e796267' : FunctionalExchange 
                        connect source ::> 'eRod_Autonomous_Vehicle_2024 Project'::'eRod_Autonomous_Vehicle_2024'::'Logical Architecture'::'Logical Functions'::'Root Logical Function'.'Detect road'.'Image fusion'.'FOP 2'
                        to target ::> 'eRod_Autonomous_Vehicle_2024 Project'::'eRod_Autonomous_Vehicle_2024'::'Logical Architecture'::'Logical Functions'::'Root Logical Function'.'Detect road'.'Detect path'.'FIP 1' { 
                        @CapellaID { eid = "362d23cd-3e2a-4128-8134-4de34e796267"; } 
                        attribute :>> isMulticast = false; 
                        attribute :>> isMultireceive = false; 
                        attribute :>> kindOfRate = RateKind::Unspecified; 
                        attribute :>> interfaceName = "Image data"; 
                    }  
                    interface 'c905054d-b98e-4384-87a6-f57316e76bce' : FunctionalExchange 
                        connect source ::> 'eRod_Autonomous_Vehicle_2024 Project'::'eRod_Autonomous_Vehicle_2024'::'Logical Architecture'::'Logical Functions'::'Root Logical Function'.'Detect road'.'Image fusion'.'FOP 3'
                        to target ::> 'eRod_Autonomous_Vehicle_2024 Project'::'eRod_Autonomous_Vehicle_2024'::'Logical Architecture'::'Logical Functions'::'Root Logical Function'.'Detect intersections'.'FIP 1' { 
                        @CapellaID { eid = "c905054d-b98e-4384-87a6-f57316e76bce"; } 
                        attribute :>> isMulticast = false; 
                        attribute :>> isMultireceive = false; 
                        attribute :>> kindOfRate = RateKind::Unspecified; 
                        attribute :>> interfaceName = "Image data"; 
                    }  
                    interface 'f5775666-3fe5-4d81-ae2b-808ebaa505f0' : FunctionalExchange 
                        connect source ::> 'eRod_Autonomous_Vehicle_2024 Project'::'eRod_Autonomous_Vehicle_2024'::'Logical Architecture'::'Logical Functions'::'Root Logical Function'.'Detect road'.'Image fusion'.'FOP 4'
                        to target ::> 'eRod_Autonomous_Vehicle_2024 Project'::'eRod_Autonomous_Vehicle_2024'::'Logical Architecture'::'Logical Functions'::'Root Logical Function'.'Detect signs'.'FIP 1' { 
                        @CapellaID { eid = "f5775666-3fe5-4d81-ae2b-808ebaa505f0"; } 
                        attribute :>> isMulticast = false; 
                        attribute :>> isMultireceive = false; 
                        attribute :>> kindOfRate = RateKind::Unspecified; 
                        attribute :>> interfaceName = "Image data"; 
                    }  
                    interface '708ee609-2bcc-471e-b075-8663624694de' : FunctionalExchange 
                        connect source ::> 'eRod_Autonomous_Vehicle_2024 Project'::'eRod_Autonomous_Vehicle_2024'::'Logical Architecture'::'Logical Functions'::'Root Logical Function'.'Detect road'.'Image fusion'.'FOP 5'
                        to target ::> 'eRod_Autonomous_Vehicle_2024 Project'::'eRod_Autonomous_Vehicle_2024'::'Logical Architecture'::'Logical Functions'::'Root Logical Function'.'Detect lights'.'FIP 1' { 
                        @CapellaID { eid = "708ee609-2bcc-471e-b075-8663624694de"; } 
                        attribute :>> isMulticast = false; 
                        attribute :>> isMultireceive = false; 
                        attribute :>> kindOfRate = RateKind::Unspecified; 
                        attribute :>> interfaceName = "Image data"; 
                    }  
                    interface '37abed24-fb61-4717-a92b-495289ca28f4' : FunctionalExchange 
                        connect source ::> 'eRod_Autonomous_Vehicle_2024 Project'::'eRod_Autonomous_Vehicle_2024'::'Logical Architecture'::'Logical Functions'::'Root Logical Function'.'Slow down and stop the vehicle'.'Measure wheel rotation speed'.'FOP 1'
                        to target ::> 'eRod_Autonomous_Vehicle_2024 Project'::'eRod_Autonomous_Vehicle_2024'::'Logical Architecture'::'Logical Functions'::'Root Logical Function'.'Slow down and stop the vehicle'.'Detect locked wheels'.'FIP 1' { 
                        @CapellaID { eid = "37abed24-fb61-4717-a92b-495289ca28f4"; } 
                        attribute :>> isMulticast = false; 
                        attribute :>> isMultireceive = false; 
                        attribute :>> kindOfRate = RateKind::Unspecified; 
                        attribute :>> interfaceName = "Wheel speed"; 
                    }  
                    interface '86e994e6-d19d-4d9f-8dea-84ea5c0194d1' : FunctionalExchange 
                        connect source ::> 'eRod_Autonomous_Vehicle_2024 Project'::'eRod_Autonomous_Vehicle_2024'::'Logical Architecture'::'Logical Functions'::'Root Logical Function'.'Slow down and stop the vehicle'.'Detect locked wheels'.'FOP 1'
                        to target ::> 'eRod_Autonomous_Vehicle_2024 Project'::'eRod_Autonomous_Vehicle_2024'::'Logical Architecture'::'Logical Functions'::'Root Logical Function'.'Slow down and stop the vehicle'.'Release brakes'.'FIP 1' { 
                        @CapellaID { eid = "86e994e6-d19d-4d9f-8dea-84ea5c0194d1"; } 
                        attribute :>> isMulticast = false; 
                        attribute :>> isMultireceive = false; 
                        attribute :>> kindOfRate = RateKind::Unspecified; 
                        attribute :>> interfaceName = "Release brakes"; 
                    }  
                    interface '1f954280-14ee-4c64-a4f8-6a722766dd58' : FunctionalExchange 
                        connect source ::> 'eRod_Autonomous_Vehicle_2024 Project'::'eRod_Autonomous_Vehicle_2024'::'Logical Architecture'::'Logical Functions'::'Root Logical Function'.'Slow down and stop the vehicle'.'Brake'.'FOP 1'
                        to target ::> 'eRod_Autonomous_Vehicle_2024 Project'::'eRod_Autonomous_Vehicle_2024'::'Logical Architecture'::'Logical Functions'::'Root Logical Function'.'Slow down and stop the vehicle'.'Apply brakes'.'FIP 1' { 
                        @CapellaID { eid = "1f954280-14ee-4c64-a4f8-6a722766dd58"; } 
                        attribute :>> isMulticast = false; 
                        attribute :>> isMultireceive = false; 
                        attribute :>> kindOfRate = RateKind::Unspecified; 
                        attribute :>> interfaceName = "Brake force"; 
                    }  
                    interface '5fa82096-df2f-4d9a-bceb-b6b4e1866e93' : FunctionalExchange 
                        connect source ::> 'eRod_Autonomous_Vehicle_2024 Project'::'eRod_Autonomous_Vehicle_2024'::'Logical Architecture'::'Logical Functions'::'Root Logical Function'.'Slow down and stop the vehicle'.'Brake'.'FOP 2'
                        to target ::> 'eRod_Autonomous_Vehicle_2024 Project'::'eRod_Autonomous_Vehicle_2024'::'Logical Architecture'::'Logical Functions'::'Root Logical Function'.'Slow down and stop the vehicle'.'Measure brake force'.'FIP 1' { 
                        @CapellaID { eid = "5fa82096-df2f-4d9a-bceb-b6b4e1866e93"; } 
                        attribute :>> isMulticast = false; 
                        attribute :>> isMultireceive = false; 
                        attribute :>> kindOfRate = RateKind::Unspecified; 
                        attribute :>> interfaceName = "Brake force"; 
                    }  
                    interface '26c2d556-5c53-4b1b-a5e6-a691d6ca7dc8' : FunctionalExchange 
                        connect source ::> 'eRod_Autonomous_Vehicle_2024 Project'::'eRod_Autonomous_Vehicle_2024'::'Logical Architecture'::'Logical Functions'::'Root Logical Function'.'Slow down and stop the vehicle'.'Measure brake force'.'FOP 1'
                        to target ::> 'eRod_Autonomous_Vehicle_2024 Project'::'eRod_Autonomous_Vehicle_2024'::'Logical Architecture'::'Logical Functions'::'Root Logical Function'.'Warn and show intent to other trafficants'.'Turn on brake lights'.'FIP 1' { 
                        @CapellaID { eid = "26c2d556-5c53-4b1b-a5e6-a691d6ca7dc8"; } 
                        attribute :>> isMulticast = false; 
                        attribute :>> isMultireceive = false; 
                        attribute :>> kindOfRate = RateKind::Unspecified; 
                        attribute :>> interfaceName = "Turn on brake lights"; 
                    }  
                    interface 'bb415348-75cd-4b1e-b9d0-f393c2124d76' : FunctionalExchange 
                        connect source ::> 'eRod_Autonomous_Vehicle_2024 Project'::'eRod_Autonomous_Vehicle_2024'::'Logical Architecture'::'Logical Functions'::'Root Logical Function'.'Drive route'.'FOP 1'
                        to target ::> 'eRod_Autonomous_Vehicle_2024 Project'::'eRod_Autonomous_Vehicle_2024'::'Logical Architecture'::'Logical Functions'::'Root Logical Function'.'Automatic Steering'.'FIP 1' { 
                        @CapellaID { eid = "bb415348-75cd-4b1e-b9d0-f393c2124d76"; } 
                        attribute :>> isMulticast = false; 
                        attribute :>> isMultireceive = false; 
                        attribute :>> kindOfRate = RateKind::Unspecified; 
                        attribute :>> interfaceName = "Steer commands"; 
                    }  
                    interface 'ad90c096-f90e-448d-ab03-d36b07193c43' : FunctionalExchange 
                        connect source ::> 'eRod_Autonomous_Vehicle_2024 Project'::'eRod_Autonomous_Vehicle_2024'::'Logical Architecture'::'Logical Functions'::'Root Logical Function'.'Apply rotation on wheels'.'FOP 1'
                        to target ::> 'eRod_Autonomous_Vehicle_2024 Project'::'eRod_Autonomous_Vehicle_2024'::'Logical Architecture'::'Logical Functions'::'Root Logical Function'.'Motor protect'.'Reduce power'.'FIP 1' { 
                        @CapellaID { eid = "ad90c096-f90e-448d-ab03-d36b07193c43"; } 
                        attribute :>> isMulticast = false; 
                        attribute :>> isMultireceive = false; 
                        attribute :>> kindOfRate = RateKind::Unspecified; 
                        attribute :>> interfaceName = "Power"; 
                         
                    }  
                    interface 'cb3b19d6-7498-488e-9920-00d4f86b6468' : FunctionalExchange 
                        connect source ::> 'eRod_Autonomous_Vehicle_2024 Project'::'eRod_Autonomous_Vehicle_2024'::'Logical Architecture'::'Logical Functions'::'Root Logical Function'.'connected to the center'.'outRe-enable'
                        to target ::> 'eRod_Autonomous_Vehicle_2024 Project'::'eRod_Autonomous_Vehicle_2024'::'Logical Architecture'::'Logical Functions'::'Root Logical Function'.'Motor Start'.'inRe-enable' { 
                        @CapellaID { eid = "cb3b19d6-7498-488e-9920-00d4f86b6468"; } 
                        attribute :>> isMulticast = false; 
                        attribute :>> isMultireceive = false; 
                        attribute :>> kindOfRate = RateKind::Unspecified; 
                        attribute :>> interfaceName = "Re-enable"; 
                         
                    }  
                    interface 'edd168dc-8fa2-4b10-a831-c8e652921b81' : FunctionalExchange 
                        connect source ::> 'eRod_Autonomous_Vehicle_2024 Project'::'eRod_Autonomous_Vehicle_2024'::'Logical Architecture'::'Logical Functions'::'Root Logical Function'.'Recieve feedback'.'outSolve'
                        to target ::> 'eRod_Autonomous_Vehicle_2024 Project'::'eRod_Autonomous_Vehicle_2024'::'Logical Architecture'::'Logical Functions'::'Root Logical Function'.'Provide solution'.'inSolve' { 
                        @CapellaID { eid = "edd168dc-8fa2-4b10-a831-c8e652921b81"; } 
                        attribute :>> isMulticast = false; 
                        attribute :>> isMultireceive = false; 
                        attribute :>> kindOfRate = RateKind::Unspecified; 
                        attribute :>> interfaceName = "Solve"; 
                         
                    }  
                    interface '5dfbe0c6-02fa-45b2-a988-7fb509b1ea5f' : FunctionalExchange 
                        connect source ::> 'eRod_Autonomous_Vehicle_2024 Project'::'eRod_Autonomous_Vehicle_2024'::'Logical Architecture'::'Logical Functions'::'Root Logical Function'.'Provide solution'.'outUpdate'
                        to target ::> 'eRod_Autonomous_Vehicle_2024 Project'::'eRod_Autonomous_Vehicle_2024'::'Logical Architecture'::'Logical Functions'::'Root Logical Function'.'Informed Software update'.'inUpdate' { 
                        @CapellaID { eid = "5dfbe0c6-02fa-45b2-a988-7fb509b1ea5f"; } 
                        attribute :>> isMulticast = false; 
                        attribute :>> isMultireceive = false; 
                        attribute :>> kindOfRate = RateKind::Unspecified; 
                        attribute :>> interfaceName = "Update"; 
                         
                    }  
                    interface 'b49f2437-ed61-4892-b964-64704b020ac3' : FunctionalExchange 
                        connect source ::> 'eRod_Autonomous_Vehicle_2024 Project'::'eRod_Autonomous_Vehicle_2024'::'Logical Architecture'::'Logical Functions'::'Root Logical Function'.'Informed Software update'.'outApproval'
                        to target ::> 'eRod_Autonomous_Vehicle_2024 Project'::'eRod_Autonomous_Vehicle_2024'::'Logical Architecture'::'Logical Functions'::'Root Logical Function'.'connected to the center'.'inApproval' { 
                        @CapellaID { eid = "b49f2437-ed61-4892-b964-64704b020ac3"; } 
                        attribute :>> isMulticast = false; 
                        attribute :>> isMultireceive = false; 
                        attribute :>> kindOfRate = RateKind::Unspecified; 
                        attribute :>> interfaceName = "Approval"; 
                         
                    }  
                    interface 'a57e94d5-e777-4b4c-aa5f-ac2d8595ac03' : FunctionalExchange 
                        connect source ::> 'eRod_Autonomous_Vehicle_2024 Project'::'eRod_Autonomous_Vehicle_2024'::'Logical Architecture'::'Logical Functions'::'Root Logical Function'.'Provide solution'.'FOP 2'
                        to target ::> 'eRod_Autonomous_Vehicle_2024 Project'::'eRod_Autonomous_Vehicle_2024'::'Logical Architecture'::'Logical Functions'::'Root Logical Function'.'Get Software-update'.'FIP 1' { 
                        @CapellaID { eid = "a57e94d5-e777-4b4c-aa5f-ac2d8595ac03"; } 
                        attribute :>> isMulticast = false; 
                        attribute :>> isMultireceive = false; 
                        attribute :>> kindOfRate = RateKind::Unspecified; 
                        attribute :>> interfaceName = "provide"; 
                         
                    }  
                    interface '4de49d8e-32ac-4c58-804a-16d3f40ee573' : FunctionalExchange 
                        connect source ::> 'eRod_Autonomous_Vehicle_2024 Project'::'eRod_Autonomous_Vehicle_2024'::'Logical Architecture'::'Logical Functions'::'Root Logical Function'.'Get Software-update'.'FOP 1'
                        to target ::> 'eRod_Autonomous_Vehicle_2024 Project'::'eRod_Autonomous_Vehicle_2024'::'Logical Architecture'::'Logical Functions'::'Root Logical Function'.'connected to the center'.'inApproval' { 
                        @CapellaID { eid = "4de49d8e-32ac-4c58-804a-16d3f40ee573"; } 
                        attribute :>> isMulticast = false; 
                        attribute :>> isMultireceive = false; 
                        attribute :>> kindOfRate = RateKind::Unspecified; 
                        attribute :>> interfaceName = "Approval"; 
                         
                    }  
                    interface 'a59d2706-68ee-49d5-9dcc-1fe46eaaac5d' : FunctionalExchange 
                        connect source ::> 'eRod_Autonomous_Vehicle_2024 Project'::'eRod_Autonomous_Vehicle_2024'::'Logical Architecture'::'Logical Functions'::'Root Logical Function'.'Maintain distance'.'FOP 1'
                        to target ::> 'eRod_Autonomous_Vehicle_2024 Project'::'eRod_Autonomous_Vehicle_2024'::'Logical Architecture'::'Logical Functions'::'Root Logical Function'.'Maintain speed'.'FIP 1' { 
                        @CapellaID { eid = "a59d2706-68ee-49d5-9dcc-1fe46eaaac5d"; } 
                        attribute :>> isMulticast = false; 
                        attribute :>> isMultireceive = false; 
                        attribute :>> kindOfRate = RateKind::Unspecified; 
                        attribute :>> interfaceName = "Set Speed"; 
                         
                    }  
                    interface '8538b361-062a-4f5b-9074-620d0f223882' : FunctionalExchange 
                        connect source ::> 'eRod_Autonomous_Vehicle_2024 Project'::'eRod_Autonomous_Vehicle_2024'::'Logical Architecture'::'Logical Functions'::'Root Logical Function'.'Activate Park Assist'.'outActivate'
                        to target ::> 'eRod_Autonomous_Vehicle_2024 Project'::'eRod_Autonomous_Vehicle_2024'::'Logical Architecture'::'Logical Functions'::'Root Logical Function'.'Status and command indication'.'inActivate' { 
                        @CapellaID { eid = "8538b361-062a-4f5b-9074-620d0f223882"; } 
                        attribute :>> isMulticast = false; 
                        attribute :>> isMultireceive = false; 
                        attribute :>> kindOfRate = RateKind::Unspecified; 
                        attribute :>> interfaceName = "Activate"; 
                         
                    }  
                    interface 'a5ebfdbf-73c1-4d59-862b-88888f9d7104' : FunctionalExchange 
                        connect source ::> 'eRod_Autonomous_Vehicle_2024 Project'::'eRod_Autonomous_Vehicle_2024'::'Logical Architecture'::'Logical Functions'::'Root Logical Function'.'Avoid collision'.'FOP 1'
                        to target ::> 'eRod_Autonomous_Vehicle_2024 Project'::'eRod_Autonomous_Vehicle_2024'::'Logical Architecture'::'Logical Functions'::'Root Logical Function'.'Slow down and stop the vehicle'.'FIP 1' { 
                        @CapellaID { eid = "a5ebfdbf-73c1-4d59-862b-88888f9d7104"; } 
                        attribute :>> isMulticast = false; 
                        attribute :>> isMultireceive = false; 
                        attribute :>> kindOfRate = RateKind::Unspecified; 
                        attribute :>> interfaceName = "Brake Command"; 
                         
                    }  
                    interface 'd18a222b-3410-46f6-a2c5-3b0367587d3a' : FunctionalExchange 
                        connect source ::> 'eRod_Autonomous_Vehicle_2024 Project'::'eRod_Autonomous_Vehicle_2024'::'Logical Architecture'::'Logical Functions'::'Root Logical Function'.'Locate targets'.'FOP 1'
                        to target ::> 'eRod_Autonomous_Vehicle_2024 Project'::'eRod_Autonomous_Vehicle_2024'::'Logical Architecture'::'Logical Functions'::'Root Logical Function'.'Avoid collision'.'FIP 1' { 
                        @CapellaID { eid = "d18a222b-3410-46f6-a2c5-3b0367587d3a"; } 
                        attribute :>> isMulticast = false; 
                        attribute :>> isMultireceive = false; 
                        attribute :>> kindOfRate = RateKind::Unspecified; 
                        attribute :>> interfaceName = "Locate Targets"; 
                         
                    }  
                    interface '87b8ca06-8640-467a-acf3-2885332412f6' : FunctionalExchange 
                        connect source ::> 'eRod_Autonomous_Vehicle_2024 Project'::'eRod_Autonomous_Vehicle_2024'::'Logical Architecture'::'Logical Functions'::'Root Logical Function'.'Provide object location'.'FOP 1'
                        to target ::> 'eRod_Autonomous_Vehicle_2024 Project'::'eRod_Autonomous_Vehicle_2024'::'Logical Architecture'::'Logical Functions'::'Root Logical Function'.'Locate targets'.'FIP 1' { 
                        @CapellaID { eid = "87b8ca06-8640-467a-acf3-2885332412f6"; } 
                        attribute :>> isMulticast = false; 
                        attribute :>> isMultireceive = false; 
                        attribute :>> kindOfRate = RateKind::Unspecified; 
                        attribute :>> interfaceName = "Object Location"; 
                         
                    }  
                    interface 'cef1d025-c3a0-42bb-88c0-9916d1773272' : FunctionalExchange 
                        connect source ::> 'eRod_Autonomous_Vehicle_2024 Project'::'eRod_Autonomous_Vehicle_2024'::'Logical Architecture'::'Logical Functions'::'Root Logical Function'.'Slow down and stop the vehicle'.'outDeceleration'
                        to target ::> 'eRod_Autonomous_Vehicle_2024 Project'::'eRod_Autonomous_Vehicle_2024'::'Logical Architecture'::'Logical Functions'::'Root Logical Function'.'Deliver traction to surface'.'inDeceleration' { 
                        @CapellaID { eid = "cef1d025-c3a0-42bb-88c0-9916d1773272"; } 
                        attribute :>> isMulticast = false; 
                        attribute :>> isMultireceive = false; 
                        attribute :>> kindOfRate = RateKind::Unspecified; 
                        attribute :>> interfaceName = "Deceleration"; 
                         
                    }  
                    interface '9f372622-48b8-4830-944f-8ee72350a823' : FunctionalExchange 
                        connect source ::> 'eRod_Autonomous_Vehicle_2024 Project'::'eRod_Autonomous_Vehicle_2024'::'Logical Architecture'::'Logical Functions'::'Root Logical Function'.'Maintain distance'.'FOP 2'
                        to target ::> 'eRod_Autonomous_Vehicle_2024 Project'::'eRod_Autonomous_Vehicle_2024'::'Logical Architecture'::'Logical Functions'::'Root Logical Function'.'Slow down and stop the vehicle'.'FIP 2' { 
                        @CapellaID { eid = "9f372622-48b8-4830-944f-8ee72350a823"; } 
                        attribute :>> isMulticast = false; 
                        attribute :>> isMultireceive = false; 
                        attribute :>> kindOfRate = RateKind::Unspecified; 
                        attribute :>> interfaceName = "Active Braking"; 
                         
                    }  
                    interface '1d2d957e-522b-46de-9966-9b91c4836e11' : FunctionalExchange 
                        connect source ::> 'eRod_Autonomous_Vehicle_2024 Project'::'eRod_Autonomous_Vehicle_2024'::'Logical Architecture'::'Logical Functions'::'Root Logical Function'.'Maintain distance'.'FOP 3'
                        to target ::> 'eRod_Autonomous_Vehicle_2024 Project'::'eRod_Autonomous_Vehicle_2024'::'Logical Architecture'::'Logical Functions'::'Root Logical Function'.'Slow down and stop the vehicle'.'FIP 3' { 
                        @CapellaID { eid = "1d2d957e-522b-46de-9966-9b91c4836e11"; } 
                        attribute :>> isMulticast = false; 
                        attribute :>> isMultireceive = false; 
                        attribute :>> kindOfRate = RateKind::Unspecified; 
                        attribute :>> interfaceName = "Brake Command"; 
                         
                    }  
                    interface '5b797939-566e-4e8d-967f-5a613f57fcdf' : FunctionalExchange 
                        connect source ::> 'eRod_Autonomous_Vehicle_2024 Project'::'eRod_Autonomous_Vehicle_2024'::'Logical Architecture'::'Logical Functions'::'Root Logical Function'.'Slow down and stop the vehicle'.'FOP 1'
                        to target ::> 'eRod_Autonomous_Vehicle_2024 Project'::'eRod_Autonomous_Vehicle_2024'::'Logical Architecture'::'Logical Functions'::'Root Logical Function'.'Maintain distance'.'FIP 1' { 
                        @CapellaID { eid = "5b797939-566e-4e8d-967f-5a613f57fcdf"; } 
                        attribute :>> isMulticast = false; 
                        attribute :>> isMultireceive = false; 
                        attribute :>> kindOfRate = RateKind::Unspecified; 
                        attribute :>> interfaceName = "Braking"; 
                         
                    }  
                    interface 'e8a1b447-aae8-462f-83d2-e68efe8d3ed1' : FunctionalExchange 
                        connect source ::> 'eRod_Autonomous_Vehicle_2024 Project'::'eRod_Autonomous_Vehicle_2024'::'Logical Architecture'::'Logical Functions'::'Root Logical Function'.'Provide vehicle status'.'FOP 1'
                        to target ::> 'eRod_Autonomous_Vehicle_2024 Project'::'eRod_Autonomous_Vehicle_2024'::'Logical Architecture'::'Logical Functions'::'Root Logical Function'.'Observe status'.'FIP 1' { 
                        @CapellaID { eid = "e8a1b447-aae8-462f-83d2-e68efe8d3ed1"; } 
                        attribute :>> isMulticast = false; 
                        attribute :>> isMultireceive = false; 
                        attribute :>> kindOfRate = RateKind::Unspecified; 
                        attribute :>> interfaceName = "Status"; 
                         
                    }  
                    interface '5684217c-ef08-4a13-a10f-2be25d9ef9bf' : FunctionalExchange 
                        connect source ::> 'eRod_Autonomous_Vehicle_2024 Project'::'eRod_Autonomous_Vehicle_2024'::'Logical Architecture'::'Logical Functions'::'Root Logical Function'.'Avoid collision'.'FOP 2'
                        to target ::> 'eRod_Autonomous_Vehicle_2024 Project'::'eRod_Autonomous_Vehicle_2024'::'Logical Architecture'::'Logical Functions'::'Root Logical Function'.'Provide vehicle status'.'FIP 1' { 
                        @CapellaID { eid = "5684217c-ef08-4a13-a10f-2be25d9ef9bf"; } 
                        attribute :>> isMulticast = false; 
                        attribute :>> isMultireceive = false; 
                        attribute :>> kindOfRate = RateKind::Unspecified; 
                        attribute :>> interfaceName = "Collsion Warning"; 
                         
                    }  
                    interface '94b73d74-b009-4feb-8fe1-ab408ade5c40' : FunctionalExchange 
                        connect source ::> 'eRod_Autonomous_Vehicle_2024 Project'::'eRod_Autonomous_Vehicle_2024'::'Logical Architecture'::'Logical Functions'::'Root Logical Function'.'Locate targets'.'FOP 2'
                        to target ::> 'eRod_Autonomous_Vehicle_2024 Project'::'eRod_Autonomous_Vehicle_2024'::'Logical Architecture'::'Logical Functions'::'Root Logical Function'.'Maintain distance'.'FIP 2' { 
                        @CapellaID { eid = "94b73d74-b009-4feb-8fe1-ab408ade5c40"; } 
                        attribute :>> isMulticast = false; 
                        attribute :>> isMultireceive = false; 
                        attribute :>> kindOfRate = RateKind::Unspecified; 
                        attribute :>> interfaceName = "Target Locations"; 
                         
                    }  
                    interface '774ae67e-2aeb-4f3a-8957-c8211a532afe' : FunctionalExchange 
                        connect source ::> 'eRod_Autonomous_Vehicle_2024 Project'::'eRod_Autonomous_Vehicle_2024'::'Logical Architecture'::'Logical Functions'::'Root Logical Function'.'Automatic Steering'.'FOP 1'
                        to target ::> 'eRod_Autonomous_Vehicle_2024 Project'::'eRod_Autonomous_Vehicle_2024'::'Logical Architecture'::'Logical Functions'::'Root Logical Function'.'Steer Wheels'.'Steer Command' { 
                        @CapellaID { eid = "774ae67e-2aeb-4f3a-8957-c8211a532afe"; } 
                        attribute :>> isMulticast = false; 
                        attribute :>> isMultireceive = false; 
                        attribute :>> kindOfRate = RateKind::Unspecified; 
                        attribute :>> interfaceName = "Steer command"; 
                         
                    }  
                    interface '1cf337b5-07c4-4d1e-91a1-033468b049db' : FunctionalExchange 
                        connect source ::> 'eRod_Autonomous_Vehicle_2024 Project'::'eRod_Autonomous_Vehicle_2024'::'Logical Architecture'::'Logical Functions'::'Root Logical Function'.'Avoid collision'.'FOP 3'
                        to target ::> 'eRod_Autonomous_Vehicle_2024 Project'::'eRod_Autonomous_Vehicle_2024'::'Logical Architecture'::'Logical Functions'::'Root Logical Function'.'Automatic Steering'.'FIP 2' { 
                        @CapellaID { eid = "1cf337b5-07c4-4d1e-91a1-033468b049db"; } 
                        attribute :>> isMulticast = false; 
                        attribute :>> isMultireceive = false; 
                        attribute :>> kindOfRate = RateKind::Unspecified; 
                        attribute :>> interfaceName = "Evasive manuever"; 
                         
                    }  
                    interface '4f4af8a7-2552-44e8-8765-3c593ad81912' : FunctionalExchange 
                        connect source ::> 'eRod_Autonomous_Vehicle_2024 Project'::'eRod_Autonomous_Vehicle_2024'::'Logical Architecture'::'Logical Functions'::'Root Logical Function'.'Drive vehicle'.'FOP 1'
                        to target ::> 'eRod_Autonomous_Vehicle_2024 Project'::'eRod_Autonomous_Vehicle_2024'::'Logical Architecture'::'Logical Functions'::'Root Logical Function'.'Steer Wheels'.'Steer Angle' { 
                        @CapellaID { eid = "4f4af8a7-2552-44e8-8765-3c593ad81912"; } 
                        attribute :>> isMulticast = false; 
                        attribute :>> isMultireceive = false; 
                        attribute :>> kindOfRate = RateKind::Unspecified; 
                        attribute :>> interfaceName = "Steering angle"; 
                         
                    }  
                    interface '73c0fd18-6786-4434-9f4c-6eec548197c5' : FunctionalExchange 
                        connect source ::> 'eRod_Autonomous_Vehicle_2024 Project'::'eRod_Autonomous_Vehicle_2024'::'Logical Architecture'::'Logical Functions'::'Root Logical Function'.'Provide road markers'.'FOP 1'
                        to target ::> 'eRod_Autonomous_Vehicle_2024 Project'::'eRod_Autonomous_Vehicle_2024'::'Logical Architecture'::'Logical Functions'::'Root Logical Function'.'Detect road'.'Capture view'.'FIP 1' { 
                        @CapellaID { eid = "73c0fd18-6786-4434-9f4c-6eec548197c5"; } 
                        attribute :>> isMulticast = false; 
                        attribute :>> isMultireceive = false; 
                        attribute :>> kindOfRate = RateKind::Unspecified; 
                        attribute :>> interfaceName = "Road markers"; 
                         
                    }  
                    interface '6dcb3416-8c5a-458c-875a-cd995816b985' : FunctionalExchange 
                        connect source ::> 'eRod_Autonomous_Vehicle_2024 Project'::'eRod_Autonomous_Vehicle_2024'::'Logical Architecture'::'Logical Functions'::'Root Logical Function'.'Detect road'.'Detect path'.'FOP 1'
                        to target ::> 'eRod_Autonomous_Vehicle_2024 Project'::'eRod_Autonomous_Vehicle_2024'::'Logical Architecture'::'Logical Functions'::'Root Logical Function'.'Automatic Steering'.'St Cmds' { 
                        @CapellaID { eid = "6dcb3416-8c5a-458c-875a-cd995816b985"; } 
                        attribute :>> isMulticast = false; 
                        attribute :>> isMultireceive = false; 
                        attribute :>> kindOfRate = RateKind::Unspecified; 
                        attribute :>> interfaceName = "Steering commands"; 
                         
                    }  
                    interface '2659f7a0-916a-49ea-9d12-eab9a18e2a75' : FunctionalExchange 
                        connect source ::> 'eRod_Autonomous_Vehicle_2024 Project'::'eRod_Autonomous_Vehicle_2024'::'Logical Architecture'::'Logical Functions'::'Root Logical Function'.'Provide target vehicle velocity'.'FOP 1'
                        to target ::> 'eRod_Autonomous_Vehicle_2024 Project'::'eRod_Autonomous_Vehicle_2024'::'Logical Architecture'::'Logical Functions'::'Root Logical Function'.'Locate targets'.'FIP 2' { 
                        @CapellaID { eid = "2659f7a0-916a-49ea-9d12-eab9a18e2a75"; } 
                        attribute :>> isMulticast = false; 
                        attribute :>> isMultireceive = false; 
                        attribute :>> kindOfRate = RateKind::Unspecified; 
                        attribute :>> interfaceName = "Target vehicle velocity"; 
                         
                    }  
                    interface 'fe17c8d3-e8bb-40ed-bd81-e495271faa01' : FunctionalExchange 
                        connect source ::> 'eRod_Autonomous_Vehicle_2024 Project'::'eRod_Autonomous_Vehicle_2024'::'Logical Architecture'::'Logical Functions'::'Root Logical Function'.'Provide target vehicle velocity'.'FOP 2'
                        to target ::> 'eRod_Autonomous_Vehicle_2024 Project'::'eRod_Autonomous_Vehicle_2024'::'Logical Architecture'::'Logical Functions'::'Root Logical Function'.'Locate targets'.'FIP 3' { 
                        @CapellaID { eid = "fe17c8d3-e8bb-40ed-bd81-e495271faa01"; } 
                        attribute :>> isMulticast = false; 
                        attribute :>> isMultireceive = false; 
                        attribute :>> kindOfRate = RateKind::Unspecified; 
                        attribute :>> interfaceName = "Target vehicle distance"; 
                         
                    }  
                    interface 'b098fdef-75c1-4260-9be0-dbeb589d16a8' : FunctionalExchange 
                        connect source ::> 'eRod_Autonomous_Vehicle_2024 Project'::'eRod_Autonomous_Vehicle_2024'::'Logical Architecture'::'Logical Functions'::'Root Logical Function'.'Drive vehicle'.'FOP 2'
                        to target ::> 'eRod_Autonomous_Vehicle_2024 Project'::'eRod_Autonomous_Vehicle_2024'::'Logical Architecture'::'Logical Functions'::'Root Logical Function'.'Slow down and stop the vehicle'.'Brake'.'FIP 1' { 
                        @CapellaID { eid = "b098fdef-75c1-4260-9be0-dbeb589d16a8"; } 
                        attribute :>> isMulticast = false; 
                        attribute :>> isMultireceive = false; 
                        attribute :>> kindOfRate = RateKind::Unspecified; 
                        attribute :>> interfaceName = "Brake"; 
                         
                    }  
                    interface '3af06698-4776-404e-a311-2894e5f52113' : FunctionalExchange 
                        connect source ::> 'eRod_Autonomous_Vehicle_2024 Project'::'eRod_Autonomous_Vehicle_2024'::'Logical Architecture'::'Logical Functions'::'Root Logical Function'.'Drive vehicle'.'FOP 3'
                        to target ::> 'eRod_Autonomous_Vehicle_2024 Project'::'eRod_Autonomous_Vehicle_2024'::'Logical Architecture'::'Logical Functions'::'Root Logical Function'.'Maintain speed'.'FIP 2' { 
                        @CapellaID { eid = "3af06698-4776-404e-a311-2894e5f52113"; } 
                        attribute :>> isMulticast = false; 
                        attribute :>> isMultireceive = false; 
                        attribute :>> kindOfRate = RateKind::Unspecified; 
                        attribute :>> interfaceName = "Accel/Decel"; 
                         
                    }  
                    interface '1d236bc3-39f0-43d8-8426-1cf5bd694aac' : FunctionalExchange 
                        connect source ::> 'eRod_Autonomous_Vehicle_2024 Project'::'eRod_Autonomous_Vehicle_2024'::'Logical Architecture'::'Logical Functions'::'Root Logical Function'.'Status and command indication'.'outRequest parking'
                        to target ::> 'eRod_Autonomous_Vehicle_2024 Project'::'eRod_Autonomous_Vehicle_2024'::'Logical Architecture'::'Logical Functions'::'Root Logical Function'.'Park vehicle'.'inRequest parking' { 
                        @CapellaID { eid = "1d236bc3-39f0-43d8-8426-1cf5bd694aac"; } 
                        attribute :>> isMulticast = false; 
                        attribute :>> isMultireceive = false; 
                        attribute :>> kindOfRate = RateKind::Unspecified; 
                        attribute :>> interfaceName = "Request parking"; 
                         
                    }  
                    interface 'af8edaa5-bd3e-4221-867b-3e330b16bbb7' : FunctionalExchange 
                        connect source ::> 'eRod_Autonomous_Vehicle_2024 Project'::'eRod_Autonomous_Vehicle_2024'::'Logical Architecture'::'Logical Functions'::'Root Logical Function'.'Provide weather'.'outWeather'
                        to target ::> 'eRod_Autonomous_Vehicle_2024 Project'::'eRod_Autonomous_Vehicle_2024'::'Logical Architecture'::'Logical Functions'::'Root Logical Function'.'Provide diverse terrain'.'inWeather' { 
                        @CapellaID { eid = "af8edaa5-bd3e-4221-867b-3e330b16bbb7"; } 
                        attribute :>> isMulticast = false; 
                        attribute :>> isMultireceive = false; 
                        attribute :>> kindOfRate = RateKind::Unspecified; 
                        attribute :>> interfaceName = "Weather"; 
                         
                    }  
                    interface 'd3d4eea1-564e-445c-9607-1f49df308576' : FunctionalExchange 
                        connect source ::> 'eRod_Autonomous_Vehicle_2024 Project'::'eRod_Autonomous_Vehicle_2024'::'Logical Architecture'::'Logical Functions'::'Root Logical Function'.'Provide diverse terrain'.'outTerrain'
                        to target ::> 'eRod_Autonomous_Vehicle_2024 Project'::'eRod_Autonomous_Vehicle_2024'::'Logical Architecture'::'Logical Functions'::'Root Logical Function'.'Drive vehicle'.'inTerrain' { 
                        @CapellaID { eid = "d3d4eea1-564e-445c-9607-1f49df308576"; } 
                        attribute :>> isMulticast = false; 
                        attribute :>> isMultireceive = false; 
                        attribute :>> kindOfRate = RateKind::Unspecified; 
                        attribute :>> interfaceName = "Terrain"; 
                         
                    }  
                    interface '1ddea015-744f-44e6-916e-f1d14e574e03' : FunctionalExchange 
                        connect source ::> 'eRod_Autonomous_Vehicle_2024 Project'::'eRod_Autonomous_Vehicle_2024'::'Logical Architecture'::'Logical Functions'::'Root Logical Function'.'Activate Park Assist'.'outDeactivate'
                        to target ::> 'eRod_Autonomous_Vehicle_2024 Project'::'eRod_Autonomous_Vehicle_2024'::'Logical Architecture'::'Logical Functions'::'Root Logical Function'.'Status and command indication'.'inDeactivate' { 
                        @CapellaID { eid = "1ddea015-744f-44e6-916e-f1d14e574e03"; } 
                        attribute :>> isMulticast = false; 
                        attribute :>> isMultireceive = false; 
                        attribute :>> kindOfRate = RateKind::Unspecified; 
                        attribute :>> interfaceName = "Deactivate"; 
                         
                    }  
                    interface 'ad62812e-8343-4a76-9456-0dc6ff29d0d0' : FunctionalExchange 
                        connect source ::> 'eRod_Autonomous_Vehicle_2024 Project'::'eRod_Autonomous_Vehicle_2024'::'Logical Architecture'::'Logical Functions'::'Root Logical Function'.'Drive vehicle'.'outLocation'
                        to target ::> 'eRod_Autonomous_Vehicle_2024 Project'::'eRod_Autonomous_Vehicle_2024'::'Logical Architecture'::'Logical Functions'::'Root Logical Function'.'Provide diverse terrain'.'inLocation' { 
                        @CapellaID { eid = "ad62812e-8343-4a76-9456-0dc6ff29d0d0"; } 
                        attribute :>> isMulticast = false; 
                        attribute :>> isMultireceive = false; 
                        attribute :>> kindOfRate = RateKind::Unspecified; 
                        attribute :>> interfaceName = "Location"; 
                         
                    }  
                    interface '2a699126-b079-4636-a460-b105a20b3c76' : FunctionalExchange 
                        connect source ::> 'eRod_Autonomous_Vehicle_2024 Project'::'eRod_Autonomous_Vehicle_2024'::'Logical Architecture'::'Logical Functions'::'Root Logical Function'.'Move objects'.'outObjects'
                        to target ::> 'eRod_Autonomous_Vehicle_2024 Project'::'eRod_Autonomous_Vehicle_2024'::'Logical Architecture'::'Logical Functions'::'Root Logical Function'.'Drive vehicle'.'inObjects' { 
                        @CapellaID { eid = "2a699126-b079-4636-a460-b105a20b3c76"; } 
                        attribute :>> isMulticast = false; 
                        attribute :>> isMultireceive = false; 
                        attribute :>> kindOfRate = RateKind::Unspecified; 
                        attribute :>> interfaceName = "Objects"; 
                         
                    }  
                    interface 'b95fdec6-d105-465f-9f2c-3a586cd5a624' : FunctionalExchange 
                        connect source ::> 'eRod_Autonomous_Vehicle_2024 Project'::'eRod_Autonomous_Vehicle_2024'::'Logical Architecture'::'Logical Functions'::'Root Logical Function'.'Reflect light'.'FOP 1'
                        to target ::> 'eRod_Autonomous_Vehicle_2024 Project'::'eRod_Autonomous_Vehicle_2024'::'Logical Architecture'::'Logical Functions'::'Root Logical Function'.'Detect road'.'Capture view'.'FIP 2' { 
                        @CapellaID { eid = "b95fdec6-d105-465f-9f2c-3a586cd5a624"; } 
                        attribute :>> isMulticast = false; 
                        attribute :>> isMultireceive = false; 
                        attribute :>> kindOfRate = RateKind::Unspecified; 
                        attribute :>> interfaceName = "Reflected light"; 
                    }  
                    interface 'ae4ff77f-fec6-4f85-bbe6-cade3bb35824' : FunctionalExchange 
                        connect source ::> 'eRod_Autonomous_Vehicle_2024 Project'::'eRod_Autonomous_Vehicle_2024'::'Logical Architecture'::'Logical Functions'::'Root Logical Function'.'Steer Wheels'.'FOP 1'
                        to target ::> 'eRod_Autonomous_Vehicle_2024 Project'::'eRod_Autonomous_Vehicle_2024'::'Logical Architecture'::'Logical Functions'::'Root Logical Function'.'Resist Front Wheels'.'FIP 1' { 
                        @CapellaID { eid = "ae4ff77f-fec6-4f85-bbe6-cade3bb35824"; } 
                        attribute :>> isMulticast = false; 
                        attribute :>> isMultireceive = false; 
                        attribute :>> kindOfRate = RateKind::Unspecified; 
                        attribute :>> interfaceName = "Wheel Angles Wheel Forces"; 
                         
                    }  
                    interface 'bf6038d4-313e-4be9-b94c-1d69db48b20f' : FunctionalExchange 
                        connect source ::> 'eRod_Autonomous_Vehicle_2024 Project'::'eRod_Autonomous_Vehicle_2024'::'Logical Architecture'::'Logical Functions'::'Root Logical Function'.'Status and command indication'.'outParking Status'
                        to target ::> 'eRod_Autonomous_Vehicle_2024 Project'::'eRod_Autonomous_Vehicle_2024'::'Logical Architecture'::'Logical Functions'::'Root Logical Function'.'Receive Status of Progess '.'inParking Status' { 
                        @CapellaID { eid = "bf6038d4-313e-4be9-b94c-1d69db48b20f"; } 
                        attribute :>> isMulticast = false; 
                        attribute :>> isMultireceive = false; 
                        attribute :>> kindOfRate = RateKind::Unspecified; 
                        attribute :>> interfaceName = "Parking Status"; 
                         
                    }  
                    interface '063a9be7-765d-4a01-a4af-024d87dfc0f7' : FunctionalExchange 
                        connect source ::> 'eRod_Autonomous_Vehicle_2024 Project'::'eRod_Autonomous_Vehicle_2024'::'Logical Architecture'::'Logical Functions'::'Root Logical Function'.'Maintain distance'.'outActive braking'
                        to target ::> 'eRod_Autonomous_Vehicle_2024 Project'::'eRod_Autonomous_Vehicle_2024'::'Logical Architecture'::'Logical Functions'::'Root Logical Function'.'Slow down and stop the vehicle'.'inActive braking' { 
                        @CapellaID { eid = "063a9be7-765d-4a01-a4af-024d87dfc0f7"; } 
                        attribute :>> isMulticast = false; 
                        attribute :>> isMultireceive = false; 
                        attribute :>> kindOfRate = RateKind::Unspecified; 
                        attribute :>> interfaceName = "Active braking"; 
                         
                    }  
                    interface '301bd8ac-cfac-4b29-ad12-48ea68fcef3e' : FunctionalExchange 
                        connect source ::> 'eRod_Autonomous_Vehicle_2024 Project'::'eRod_Autonomous_Vehicle_2024'::'Logical Architecture'::'Logical Functions'::'Root Logical Function'.'Vehicle Command'.'outVehicle Commands'
                        to target ::> 'eRod_Autonomous_Vehicle_2024 Project'::'eRod_Autonomous_Vehicle_2024'::'Logical Architecture'::'Logical Functions'::'Root Logical Function'.'Remote Operate Car'.'inVehicle Commands' { 
                        @CapellaID { eid = "301bd8ac-cfac-4b29-ad12-48ea68fcef3e"; } 
                        attribute :>> isMulticast = false; 
                        attribute :>> isMultireceive = false; 
                        attribute :>> kindOfRate = RateKind::Unspecified; 
                        attribute :>> interfaceName = "Vehicle Commands"; 
                         
                    }  
                    interface '3ffc52b3-84cc-4e46-b9a1-73b4477f0db4' : FunctionalExchange 
                        connect source ::> 'eRod_Autonomous_Vehicle_2024 Project'::'eRod_Autonomous_Vehicle_2024'::'Logical Architecture'::'Logical Functions'::'Root Logical Function'.'Remote Operate Car'.'outInitiate Park'
                        to target ::> 'eRod_Autonomous_Vehicle_2024 Project'::'eRod_Autonomous_Vehicle_2024'::'Logical Architecture'::'Logical Functions'::'Root Logical Function'.'Park vehicle'.'inInitiate Park' { 
                        @CapellaID { eid = "3ffc52b3-84cc-4e46-b9a1-73b4477f0db4"; } 
                        attribute :>> isMulticast = false; 
                        attribute :>> isMultireceive = false; 
                        attribute :>> kindOfRate = RateKind::Unspecified; 
                        attribute :>> interfaceName = "Initiate Park"; 
                         
                    }  
                    interface '065c228b-18bd-43b7-818c-46cd338ea62c' : FunctionalExchange 
                        connect source ::> 'eRod_Autonomous_Vehicle_2024 Project'::'eRod_Autonomous_Vehicle_2024'::'Logical Architecture'::'Logical Functions'::'Root Logical Function'.'Steer Wheels Remote'.'outWheel Position'
                        to target ::> 'eRod_Autonomous_Vehicle_2024 Project'::'eRod_Autonomous_Vehicle_2024'::'Logical Architecture'::'Logical Functions'::'Root Logical Function'.'Deliver traction to surface'.'inWheel Position' { 
                        @CapellaID { eid = "065c228b-18bd-43b7-818c-46cd338ea62c"; } 
                        attribute :>> isMulticast = false; 
                        attribute :>> isMultireceive = false; 
                        attribute :>> kindOfRate = RateKind::Unspecified; 
                        attribute :>> interfaceName = "Wheel Position"; 
                         
                    }  
                    interface '93262ba9-6596-4b5f-b46b-4fd1ddf0d744' : FunctionalExchange 
                        connect source ::> 'eRod_Autonomous_Vehicle_2024 Project'::'eRod_Autonomous_Vehicle_2024'::'Logical Architecture'::'Logical Functions'::'Root Logical Function'.'Park vehicle'.'outBraking Commands'
                        to target ::> 'eRod_Autonomous_Vehicle_2024 Project'::'eRod_Autonomous_Vehicle_2024'::'Logical Architecture'::'Logical Functions'::'Root Logical Function'.'Control Accel'.'inBraking Commands' { 
                        @CapellaID { eid = "93262ba9-6596-4b5f-b46b-4fd1ddf0d744"; } 
                        attribute :>> isMulticast = false; 
                        attribute :>> isMultireceive = false; 
                        attribute :>> kindOfRate = RateKind::Unspecified; 
                        attribute :>> interfaceName = "Braking Commands"; 
                         
                    }  
                    interface '1dfbf83d-de25-4e27-8ccb-e14f31c3d4bd' : FunctionalExchange 
                        connect source ::> 'eRod_Autonomous_Vehicle_2024 Project'::'eRod_Autonomous_Vehicle_2024'::'Logical Architecture'::'Logical Functions'::'Root Logical Function'.'Park vehicle'.'outSteering Commands'
                        to target ::> 'eRod_Autonomous_Vehicle_2024 Project'::'eRod_Autonomous_Vehicle_2024'::'Logical Architecture'::'Logical Functions'::'Root Logical Function'.'Steer Wheels Remote'.'inSteering Commands' { 
                        @CapellaID { eid = "1dfbf83d-de25-4e27-8ccb-e14f31c3d4bd"; } 
                        attribute :>> isMulticast = false; 
                        attribute :>> isMultireceive = false; 
                        attribute :>> kindOfRate = RateKind::Unspecified; 
                        attribute :>> interfaceName = "Steering Commands"; 
                         
                    }  
                    interface '3100499d-8657-4e28-a511-cf0fb745cfc4' : FunctionalExchange 
                        connect source ::> 'eRod_Autonomous_Vehicle_2024 Project'::'eRod_Autonomous_Vehicle_2024'::'Logical Architecture'::'Logical Functions'::'Root Logical Function'.'Deliver traction to surface'.'outTraction'
                        to target ::> 'eRod_Autonomous_Vehicle_2024 Project'::'eRod_Autonomous_Vehicle_2024'::'Logical Architecture'::'Logical Functions'::'Root Logical Function'.'Provide diverse terrain'.'inTraction' { 
                        @CapellaID { eid = "3100499d-8657-4e28-a511-cf0fb745cfc4"; } 
                        attribute :>> isMulticast = false; 
                        attribute :>> isMultireceive = false; 
                        attribute :>> kindOfRate = RateKind::Unspecified; 
                        attribute :>> interfaceName = "Traction"; 
                         
                    }  
                    interface 'd096cac7-97a3-419f-b943-1af03c0794a9' : FunctionalExchange 
                        connect source ::> 'eRod_Autonomous_Vehicle_2024 Project'::'eRod_Autonomous_Vehicle_2024'::'Logical Architecture'::'Logical Functions'::'Root Logical Function'.'Automatic Steer'.'FOP 1'
                        to target ::> 'eRod_Autonomous_Vehicle_2024 Project'::'eRod_Autonomous_Vehicle_2024'::'Logical Architecture'::'Logical Functions'::'Root Logical Function'.'Steer Wheels'.'Auto Steer' { 
                        @CapellaID { eid = "d096cac7-97a3-419f-b943-1af03c0794a9"; } 
                        attribute :>> isMulticast = false; 
                        attribute :>> isMultireceive = false; 
                        attribute :>> kindOfRate = RateKind::Unspecified; 
                        attribute :>> interfaceName = "Auto Steeer Comand"; 
                    }  
                    interface '418ee4a5-2399-474b-be28-1165c851f3d6' : FunctionalExchange 
                        connect source ::> 'eRod_Autonomous_Vehicle_2024 Project'::'eRod_Autonomous_Vehicle_2024'::'Logical Architecture'::'Logical Functions'::'Root Logical Function'.'Control Accel'.'FOP 1'
                        to target ::> 'eRod_Autonomous_Vehicle_2024 Project'::'eRod_Autonomous_Vehicle_2024'::'Logical Architecture'::'Logical Functions'::'Root Logical Function'.'Slow down and stop the vehicle'.'FIP 7' { 
                        @CapellaID { eid = "418ee4a5-2399-474b-be28-1165c851f3d6"; } 
                        attribute :>> isMulticast = false; 
                        attribute :>> isMultireceive = false; 
                        attribute :>> kindOfRate = RateKind::Unspecified; 
                        attribute :>> interfaceName = "FunctionalExchange 95"; 
                    }  
                    interface '66d79c3e-9600-4eb7-9163-a41a826a1eb7' : FunctionalExchange 
                        connect source ::> 'eRod_Autonomous_Vehicle_2024 Project'::'eRod_Autonomous_Vehicle_2024'::'Logical Architecture'::'Logical Functions'::'Root Logical Function'.'Detect obstacles'.'FOP 1'
                        to target ::> 'eRod_Autonomous_Vehicle_2024 Project'::'eRod_Autonomous_Vehicle_2024'::'Logical Architecture'::'Logical Functions'::'Root Logical Function'.'Provide object location'.'FIP 1' { 
                        @CapellaID { eid = "66d79c3e-9600-4eb7-9163-a41a826a1eb7"; } 
                        attribute :>> isMulticast = false; 
                        attribute :>> isMultireceive = false; 
                        attribute :>> kindOfRate = RateKind::Unspecified; 
                        attribute :>> interfaceName = "FunctionalExchange 96"; 
                    }  
                    interface 'f556bb6e-428a-4906-ba9f-e0b9b35648e1' : FunctionalExchange 
                        connect source ::> 'eRod_Autonomous_Vehicle_2024 Project'::'eRod_Autonomous_Vehicle_2024'::'Logical Architecture'::'Logical Functions'::'Root Logical Function'.'Get Software-update'.'FOP 2'
                        to target ::> 'eRod_Autonomous_Vehicle_2024 Project'::'eRod_Autonomous_Vehicle_2024'::'Logical Architecture'::'Logical Functions'::'Root Logical Function'.'Obtain car racing experience'.'FIP 2' { 
                        @CapellaID { eid = "f556bb6e-428a-4906-ba9f-e0b9b35648e1"; } 
                        attribute :>> isMulticast = false; 
                        attribute :>> isMultireceive = false; 
                        attribute :>> kindOfRate = RateKind::Unspecified; 
                        attribute :>> interfaceName = "Monitor operation"; 
                    }  
                    interface '033494da-7516-44f8-a2d3-007f5e9f12cd' : FunctionalExchange 
                        connect source ::> 'eRod_Autonomous_Vehicle_2024 Project'::'eRod_Autonomous_Vehicle_2024'::'Logical Architecture'::'Logical Functions'::'Root Logical Function'.'Report issues'.'FOP 1'
                        to target ::> 'eRod_Autonomous_Vehicle_2024 Project'::'eRod_Autonomous_Vehicle_2024'::'Logical Architecture'::'Logical Functions'::'Root Logical Function'.'Recieve feedback'.'FIP 1' { 
                        @CapellaID { eid = "033494da-7516-44f8-a2d3-007f5e9f12cd"; } 
                        attribute :>> isMulticast = false; 
                        attribute :>> isMultireceive = false; 
                        attribute :>> kindOfRate = RateKind::Unspecified; 
                        attribute :>> interfaceName = "Information"; 
                    }  
                     
                    ref :>> ownedFunctions =  ('eRod_Autonomous_Vehicle_2024 Project'::'eRod_Autonomous_Vehicle_2024'::'Logical Architecture'::'Logical Functions'::'Root Logical Function'.'Drive on a race track',
                    'eRod_Autonomous_Vehicle_2024 Project'::'eRod_Autonomous_Vehicle_2024'::'Logical Architecture'::'Logical Functions'::'Root Logical Function'.'Sporty drive',
                    'eRod_Autonomous_Vehicle_2024 Project'::'eRod_Autonomous_Vehicle_2024'::'Logical Architecture'::'Logical Functions'::'Root Logical Function'.'Car racing experience absorbed',
                    'eRod_Autonomous_Vehicle_2024 Project'::'eRod_Autonomous_Vehicle_2024'::'Logical Architecture'::'Logical Functions'::'Root Logical Function'.'Motor overheating warning ',
                    'eRod_Autonomous_Vehicle_2024 Project'::'eRod_Autonomous_Vehicle_2024'::'Logical Architecture'::'Logical Functions'::'Root Logical Function'.'Software update',
                    'eRod_Autonomous_Vehicle_2024 Project'::'eRod_Autonomous_Vehicle_2024'::'Logical Architecture'::'Logical Functions'::'Root Logical Function'.'Report issues',
                    'eRod_Autonomous_Vehicle_2024 Project'::'eRod_Autonomous_Vehicle_2024'::'Logical Architecture'::'Logical Functions'::'Root Logical Function'.'Get informed with issues',
                    'eRod_Autonomous_Vehicle_2024 Project'::'eRod_Autonomous_Vehicle_2024'::'Logical Architecture'::'Logical Functions'::'Root Logical Function'.'Deaccelerate',
                    'eRod_Autonomous_Vehicle_2024 Project'::'eRod_Autonomous_Vehicle_2024'::'Logical Architecture'::'Logical Functions'::'Root Logical Function'.'Stop',
                    'eRod_Autonomous_Vehicle_2024 Project'::'eRod_Autonomous_Vehicle_2024'::'Logical Architecture'::'Logical Functions'::'Root Logical Function'.'Get Software-update',
                    'eRod_Autonomous_Vehicle_2024 Project'::'eRod_Autonomous_Vehicle_2024'::'Logical Architecture'::'Logical Functions'::'Root Logical Function'.'Obtain car racing experience',
                    'eRod_Autonomous_Vehicle_2024 Project'::'eRod_Autonomous_Vehicle_2024'::'Logical Architecture'::'Logical Functions'::'Root Logical Function'.'Transfer Energy',
                    'eRod_Autonomous_Vehicle_2024 Project'::'eRod_Autonomous_Vehicle_2024'::'Logical Architecture'::'Logical Functions'::'Root Logical Function'.'Motor protect',
                    'eRod_Autonomous_Vehicle_2024 Project'::'eRod_Autonomous_Vehicle_2024'::'Logical Architecture'::'Logical Functions'::'Root Logical Function'.'Control temperature',
                    'eRod_Autonomous_Vehicle_2024 Project'::'eRod_Autonomous_Vehicle_2024'::'Logical Architecture'::'Logical Functions'::'Root Logical Function'.'deliver mechanical power',
                    'eRod_Autonomous_Vehicle_2024 Project'::'eRod_Autonomous_Vehicle_2024'::'Logical Architecture'::'Logical Functions'::'Root Logical Function'.'Generate heat (Rotor)',
                    'eRod_Autonomous_Vehicle_2024 Project'::'eRod_Autonomous_Vehicle_2024'::'Logical Architecture'::'Logical Functions'::'Root Logical Function'.'Provide magnetic field',
                    'eRod_Autonomous_Vehicle_2024 Project'::'eRod_Autonomous_Vehicle_2024'::'Logical Architecture'::'Logical Functions'::'Root Logical Function'.'Generate Heat (Stator)',
                    'eRod_Autonomous_Vehicle_2024 Project'::'eRod_Autonomous_Vehicle_2024'::'Logical Architecture'::'Logical Functions'::'Root Logical Function'.'protect',
                    'eRod_Autonomous_Vehicle_2024 Project'::'eRod_Autonomous_Vehicle_2024'::'Logical Architecture'::'Logical Functions'::'Root Logical Function'.'Transfer heat',
                    'eRod_Autonomous_Vehicle_2024 Project'::'eRod_Autonomous_Vehicle_2024'::'Logical Architecture'::'Logical Functions'::'Root Logical Function'.'Gather 21',
                    'eRod_Autonomous_Vehicle_2024 Project'::'eRod_Autonomous_Vehicle_2024'::'Logical Architecture'::'Logical Functions'::'Root Logical Function'.'Motor Start',
                    'eRod_Autonomous_Vehicle_2024 Project'::'eRod_Autonomous_Vehicle_2024'::'Logical Architecture'::'Logical Functions'::'Root Logical Function'.'Transfer power to Axies',
                    'eRod_Autonomous_Vehicle_2024 Project'::'eRod_Autonomous_Vehicle_2024'::'Logical Architecture'::'Logical Functions'::'Root Logical Function'.'Apply rotation on wheels',
                    'eRod_Autonomous_Vehicle_2024 Project'::'eRod_Autonomous_Vehicle_2024'::'Logical Architecture'::'Logical Functions'::'Root Logical Function'.'Split 25',
                    'eRod_Autonomous_Vehicle_2024 Project'::'eRod_Autonomous_Vehicle_2024'::'Logical Architecture'::'Logical Functions'::'Root Logical Function'.'Improve motor performance',
                    'eRod_Autonomous_Vehicle_2024 Project'::'eRod_Autonomous_Vehicle_2024'::'Logical Architecture'::'Logical Functions'::'Root Logical Function'.'remote update',
                    'eRod_Autonomous_Vehicle_2024 Project'::'eRod_Autonomous_Vehicle_2024'::'Logical Architecture'::'Logical Functions'::'Root Logical Function'.'connected to the center',
                    'eRod_Autonomous_Vehicle_2024 Project'::'eRod_Autonomous_Vehicle_2024'::'Logical Architecture'::'Logical Functions'::'Root Logical Function'.'Provide electrical energy',
                    'eRod_Autonomous_Vehicle_2024 Project'::'eRod_Autonomous_Vehicle_2024'::'Logical Architecture'::'Logical Functions'::'Root Logical Function'.'Absorb bumps in the road',
                    'eRod_Autonomous_Vehicle_2024 Project'::'eRod_Autonomous_Vehicle_2024'::'Logical Architecture'::'Logical Functions'::'Root Logical Function'.'Maximize the friction between the tires and roads',
                    'eRod_Autonomous_Vehicle_2024 Project'::'eRod_Autonomous_Vehicle_2024'::'Logical Architecture'::'Logical Functions'::'Root Logical Function'.'Light up the road',
                    'eRod_Autonomous_Vehicle_2024 Project'::'eRod_Autonomous_Vehicle_2024'::'Logical Architecture'::'Logical Functions'::'Root Logical Function'.'Warn and show intent to other trafficants',
                    'eRod_Autonomous_Vehicle_2024 Project'::'eRod_Autonomous_Vehicle_2024'::'Logical Architecture'::'Logical Functions'::'Root Logical Function'.'Recieve feedback',
                    'eRod_Autonomous_Vehicle_2024 Project'::'eRod_Autonomous_Vehicle_2024'::'Logical Architecture'::'Logical Functions'::'Root Logical Function'.'Provide solution',
                    'eRod_Autonomous_Vehicle_2024 Project'::'eRod_Autonomous_Vehicle_2024'::'Logical Architecture'::'Logical Functions'::'Root Logical Function'.'Informed Software update',
                    'eRod_Autonomous_Vehicle_2024 Project'::'eRod_Autonomous_Vehicle_2024'::'Logical Architecture'::'Logical Functions'::'Root Logical Function'.'Deliver traction to surface',
                    'eRod_Autonomous_Vehicle_2024 Project'::'eRod_Autonomous_Vehicle_2024'::'Logical Architecture'::'Logical Functions'::'Root Logical Function'.'Maintain distance',
                    'eRod_Autonomous_Vehicle_2024 Project'::'eRod_Autonomous_Vehicle_2024'::'Logical Architecture'::'Logical Functions'::'Root Logical Function'.'Slow down and stop the vehicle',
                    'eRod_Autonomous_Vehicle_2024 Project'::'eRod_Autonomous_Vehicle_2024'::'Logical Architecture'::'Logical Functions'::'Root Logical Function'.'Hold vehicle in place',
                    'eRod_Autonomous_Vehicle_2024 Project'::'eRod_Autonomous_Vehicle_2024'::'Logical Architecture'::'Logical Functions'::'Root Logical Function'.'Store energy',
                    'eRod_Autonomous_Vehicle_2024 Project'::'eRod_Autonomous_Vehicle_2024'::'Logical Architecture'::'Logical Functions'::'Root Logical Function'.'Detect obstacles',
                    'eRod_Autonomous_Vehicle_2024 Project'::'eRod_Autonomous_Vehicle_2024'::'Logical Architecture'::'Logical Functions'::'Root Logical Function'.'Plan path',
                    'eRod_Autonomous_Vehicle_2024 Project'::'eRod_Autonomous_Vehicle_2024'::'Logical Architecture'::'Logical Functions'::'Root Logical Function'.'Drive route',
                    'eRod_Autonomous_Vehicle_2024 Project'::'eRod_Autonomous_Vehicle_2024'::'Logical Architecture'::'Logical Functions'::'Root Logical Function'.'Detect intersections',
                    'eRod_Autonomous_Vehicle_2024 Project'::'eRod_Autonomous_Vehicle_2024'::'Logical Architecture'::'Logical Functions'::'Root Logical Function'.'Detect signs',
                    'eRod_Autonomous_Vehicle_2024 Project'::'eRod_Autonomous_Vehicle_2024'::'Logical Architecture'::'Logical Functions'::'Root Logical Function'.'Detect lights',
                    'eRod_Autonomous_Vehicle_2024 Project'::'eRod_Autonomous_Vehicle_2024'::'Logical Architecture'::'Logical Functions'::'Root Logical Function'.'Capture points',
                    'eRod_Autonomous_Vehicle_2024 Project'::'eRod_Autonomous_Vehicle_2024'::'Logical Architecture'::'Logical Functions'::'Root Logical Function'.'Capture radar echo',
                    'eRod_Autonomous_Vehicle_2024 Project'::'eRod_Autonomous_Vehicle_2024'::'Logical Architecture'::'Logical Functions'::'Root Logical Function'.'Avoid collision',
                    'eRod_Autonomous_Vehicle_2024 Project'::'eRod_Autonomous_Vehicle_2024'::'Logical Architecture'::'Logical Functions'::'Root Logical Function'.'Provide object location',
                    'eRod_Autonomous_Vehicle_2024 Project'::'eRod_Autonomous_Vehicle_2024'::'Logical Architecture'::'Logical Functions'::'Root Logical Function'.'Observe status',
                    'eRod_Autonomous_Vehicle_2024 Project'::'eRod_Autonomous_Vehicle_2024'::'Logical Architecture'::'Logical Functions'::'Root Logical Function'.'Provide vehicle status',
                    'eRod_Autonomous_Vehicle_2024 Project'::'eRod_Autonomous_Vehicle_2024'::'Logical Architecture'::'Logical Functions'::'Root Logical Function'.'Steer Wheels',
                    'eRod_Autonomous_Vehicle_2024 Project'::'eRod_Autonomous_Vehicle_2024'::'Logical Architecture'::'Logical Functions'::'Root Logical Function'.'Measure vehicle speed',
                    'eRod_Autonomous_Vehicle_2024 Project'::'eRod_Autonomous_Vehicle_2024'::'Logical Architecture'::'Logical Functions'::'Root Logical Function'.'Locate targets',
                    'eRod_Autonomous_Vehicle_2024 Project'::'eRod_Autonomous_Vehicle_2024'::'Logical Architecture'::'Logical Functions'::'Root Logical Function'.'Maintain speed',
                    'eRod_Autonomous_Vehicle_2024 Project'::'eRod_Autonomous_Vehicle_2024'::'Logical Architecture'::'Logical Functions'::'Root Logical Function'.'Drive vehicle',
                    'eRod_Autonomous_Vehicle_2024 Project'::'eRod_Autonomous_Vehicle_2024'::'Logical Architecture'::'Logical Functions'::'Root Logical Function'.'Automatic Steering',
                    'eRod_Autonomous_Vehicle_2024 Project'::'eRod_Autonomous_Vehicle_2024'::'Logical Architecture'::'Logical Functions'::'Root Logical Function'.'Detect road',
                    'eRod_Autonomous_Vehicle_2024 Project'::'eRod_Autonomous_Vehicle_2024'::'Logical Architecture'::'Logical Functions'::'Root Logical Function'.'Provide road markers',
                    'eRod_Autonomous_Vehicle_2024 Project'::'eRod_Autonomous_Vehicle_2024'::'Logical Architecture'::'Logical Functions'::'Root Logical Function'.'Provide target vehicle velocity',
                    'eRod_Autonomous_Vehicle_2024 Project'::'eRod_Autonomous_Vehicle_2024'::'Logical Architecture'::'Logical Functions'::'Root Logical Function'.'Provide diverse terrain',
                    'eRod_Autonomous_Vehicle_2024 Project'::'eRod_Autonomous_Vehicle_2024'::'Logical Architecture'::'Logical Functions'::'Root Logical Function'.'Provide parking location',
                    'eRod_Autonomous_Vehicle_2024 Project'::'eRod_Autonomous_Vehicle_2024'::'Logical Architecture'::'Logical Functions'::'Root Logical Function'.'Steer Wheels Remote',
                    'eRod_Autonomous_Vehicle_2024 Project'::'eRod_Autonomous_Vehicle_2024'::'Logical Architecture'::'Logical Functions'::'Root Logical Function'.'Provide weather',
                    'eRod_Autonomous_Vehicle_2024 Project'::'eRod_Autonomous_Vehicle_2024'::'Logical Architecture'::'Logical Functions'::'Root Logical Function'.'Move objects',
                    'eRod_Autonomous_Vehicle_2024 Project'::'eRod_Autonomous_Vehicle_2024'::'Logical Architecture'::'Logical Functions'::'Root Logical Function'.'Reflect light',
                    'eRod_Autonomous_Vehicle_2024 Project'::'eRod_Autonomous_Vehicle_2024'::'Logical Architecture'::'Logical Functions'::'Root Logical Function'.'Resist Front Wheels',
                    'eRod_Autonomous_Vehicle_2024 Project'::'eRod_Autonomous_Vehicle_2024'::'Logical Architecture'::'Logical Functions'::'Root Logical Function'.'Park vehicle',
                    'eRod_Autonomous_Vehicle_2024 Project'::'eRod_Autonomous_Vehicle_2024'::'Logical Architecture'::'Logical Functions'::'Root Logical Function'.'Vehicle Command',
                    'eRod_Autonomous_Vehicle_2024 Project'::'eRod_Autonomous_Vehicle_2024'::'Logical Architecture'::'Logical Functions'::'Root Logical Function'.'Receive Status of Progess ',
                    'eRod_Autonomous_Vehicle_2024 Project'::'eRod_Autonomous_Vehicle_2024'::'Logical Architecture'::'Logical Functions'::'Root Logical Function'.'Activate Park Assist',
                    'eRod_Autonomous_Vehicle_2024 Project'::'eRod_Autonomous_Vehicle_2024'::'Logical Architecture'::'Logical Functions'::'Root Logical Function'.'Status and command indication',
                    'eRod_Autonomous_Vehicle_2024 Project'::'eRod_Autonomous_Vehicle_2024'::'Logical Architecture'::'Logical Functions'::'Root Logical Function'.'Remote Operate Car',
                    'eRod_Autonomous_Vehicle_2024 Project'::'eRod_Autonomous_Vehicle_2024'::'Logical Architecture'::'Logical Functions'::'Root Logical Function'.'Automatic Steer',
                    'eRod_Autonomous_Vehicle_2024 Project'::'eRod_Autonomous_Vehicle_2024'::'Logical Architecture'::'Logical Functions'::'Root Logical Function'.'Control Accel',
                    'eRod_Autonomous_Vehicle_2024 Project'::'eRod_Autonomous_Vehicle_2024'::'Logical Architecture'::'Logical Functions'::'Root Logical Function'.'Calculate Driving Path',
                    'eRod_Autonomous_Vehicle_2024 Project'::'eRod_Autonomous_Vehicle_2024'::'Logical Architecture'::'Logical Functions'::'Root Logical Function'.'Display State of Park'); 
                    ref :>> ownedFunctionalExchanges =  ('eRod_Autonomous_Vehicle_2024 Project'::'eRod_Autonomous_Vehicle_2024'::'Logical Architecture'::'Logical Functions'::'Root Logical Function'.'b953457a-88f3-40b9-a380-8bbaeb6110c8',
                    'eRod_Autonomous_Vehicle_2024 Project'::'eRod_Autonomous_Vehicle_2024'::'Logical Architecture'::'Logical Functions'::'Root Logical Function'.'49b41474-6068-48af-9f20-48587c061248',
                    'eRod_Autonomous_Vehicle_2024 Project'::'eRod_Autonomous_Vehicle_2024'::'Logical Architecture'::'Logical Functions'::'Root Logical Function'.'37640148-3029-4dd4-98be-abe69563435f',
                    'eRod_Autonomous_Vehicle_2024 Project'::'eRod_Autonomous_Vehicle_2024'::'Logical Architecture'::'Logical Functions'::'Root Logical Function'.'0e825f29-7978-4cea-92bf-ed5a75495285',
                    'eRod_Autonomous_Vehicle_2024 Project'::'eRod_Autonomous_Vehicle_2024'::'Logical Architecture'::'Logical Functions'::'Root Logical Function'.'d83bfe14-3bb0-443f-8b64-ac175f2b9aa1',
                    'eRod_Autonomous_Vehicle_2024 Project'::'eRod_Autonomous_Vehicle_2024'::'Logical Architecture'::'Logical Functions'::'Root Logical Function'.'76b26dd2-2a46-4b84-b303-1c3132586ce4',
                    'eRod_Autonomous_Vehicle_2024 Project'::'eRod_Autonomous_Vehicle_2024'::'Logical Architecture'::'Logical Functions'::'Root Logical Function'.'8284c472-1721-460b-a37b-cf61ee2657b7',
                    'eRod_Autonomous_Vehicle_2024 Project'::'eRod_Autonomous_Vehicle_2024'::'Logical Architecture'::'Logical Functions'::'Root Logical Function'.'89d97516-8ef5-40a7-98d5-18282eaded97',
                    'eRod_Autonomous_Vehicle_2024 Project'::'eRod_Autonomous_Vehicle_2024'::'Logical Architecture'::'Logical Functions'::'Root Logical Function'.'61aa0363-0061-464c-bc92-e50e39909e33',
                    'eRod_Autonomous_Vehicle_2024 Project'::'eRod_Autonomous_Vehicle_2024'::'Logical Architecture'::'Logical Functions'::'Root Logical Function'.'8db9677b-6d28-4860-959e-3ee1b2019e3b',
                    'eRod_Autonomous_Vehicle_2024 Project'::'eRod_Autonomous_Vehicle_2024'::'Logical Architecture'::'Logical Functions'::'Root Logical Function'.'74867a97-5a2c-491c-9dce-59691e217f48',
                    'eRod_Autonomous_Vehicle_2024 Project'::'eRod_Autonomous_Vehicle_2024'::'Logical Architecture'::'Logical Functions'::'Root Logical Function'.'d697c6f7-0d8d-4400-9831-689058aece59',
                    'eRod_Autonomous_Vehicle_2024 Project'::'eRod_Autonomous_Vehicle_2024'::'Logical Architecture'::'Logical Functions'::'Root Logical Function'.'6ac2dbe1-37d1-40d6-b342-7544db1c549d',
                    'eRod_Autonomous_Vehicle_2024 Project'::'eRod_Autonomous_Vehicle_2024'::'Logical Architecture'::'Logical Functions'::'Root Logical Function'.'3b2fa504-9f86-4fba-8878-a557fb2e37c6',
                    'eRod_Autonomous_Vehicle_2024 Project'::'eRod_Autonomous_Vehicle_2024'::'Logical Architecture'::'Logical Functions'::'Root Logical Function'.'c151213d-abcb-4610-894b-50fcd89715b0',
                    'eRod_Autonomous_Vehicle_2024 Project'::'eRod_Autonomous_Vehicle_2024'::'Logical Architecture'::'Logical Functions'::'Root Logical Function'.'a4b7ed98-d219-4ab0-afad-a46848adc7ad',
                    'eRod_Autonomous_Vehicle_2024 Project'::'eRod_Autonomous_Vehicle_2024'::'Logical Architecture'::'Logical Functions'::'Root Logical Function'.'285ee071-9867-4f7f-abaf-dfbfeff65f67',
                    'eRod_Autonomous_Vehicle_2024 Project'::'eRod_Autonomous_Vehicle_2024'::'Logical Architecture'::'Logical Functions'::'Root Logical Function'.'819c5300-ab95-4dc1-875a-b233e8abdfac',
                    'eRod_Autonomous_Vehicle_2024 Project'::'eRod_Autonomous_Vehicle_2024'::'Logical Architecture'::'Logical Functions'::'Root Logical Function'.'f0a7c5c5-8077-4718-bf83-a61a4cf56123',
                    'eRod_Autonomous_Vehicle_2024 Project'::'eRod_Autonomous_Vehicle_2024'::'Logical Architecture'::'Logical Functions'::'Root Logical Function'.'fbab703c-b455-4208-af50-8fe4d4c8d693',
                    'eRod_Autonomous_Vehicle_2024 Project'::'eRod_Autonomous_Vehicle_2024'::'Logical Architecture'::'Logical Functions'::'Root Logical Function'.'ac15c188-c849-4add-8db5-5c783d913d61',
                    'eRod_Autonomous_Vehicle_2024 Project'::'eRod_Autonomous_Vehicle_2024'::'Logical Architecture'::'Logical Functions'::'Root Logical Function'.'690b4231-60c3-43fd-ae81-d3f3f2d64519',
                    'eRod_Autonomous_Vehicle_2024 Project'::'eRod_Autonomous_Vehicle_2024'::'Logical Architecture'::'Logical Functions'::'Root Logical Function'.'3b5e8600-d938-4502-bd08-5d95e69970d5',
                    'eRod_Autonomous_Vehicle_2024 Project'::'eRod_Autonomous_Vehicle_2024'::'Logical Architecture'::'Logical Functions'::'Root Logical Function'.'1cbd00ec-4044-4944-96b5-97902f698ad7',
                    'eRod_Autonomous_Vehicle_2024 Project'::'eRod_Autonomous_Vehicle_2024'::'Logical Architecture'::'Logical Functions'::'Root Logical Function'.'ad75ca27-9657-4f7a-b9f0-91f8f72375b0',
                    'eRod_Autonomous_Vehicle_2024 Project'::'eRod_Autonomous_Vehicle_2024'::'Logical Architecture'::'Logical Functions'::'Root Logical Function'.'9834ba0a-fa40-4c5c-b41c-f4eab563640f',
                    'eRod_Autonomous_Vehicle_2024 Project'::'eRod_Autonomous_Vehicle_2024'::'Logical Architecture'::'Logical Functions'::'Root Logical Function'.'ffd7802c-2093-4298-a18f-a98778d74812',
                    'eRod_Autonomous_Vehicle_2024 Project'::'eRod_Autonomous_Vehicle_2024'::'Logical Architecture'::'Logical Functions'::'Root Logical Function'.'36b16c46-58ff-4544-a888-051ef74aa3f1',
                    'eRod_Autonomous_Vehicle_2024 Project'::'eRod_Autonomous_Vehicle_2024'::'Logical Architecture'::'Logical Functions'::'Root Logical Function'.'19d12ee0-70a6-49d7-9468-396730331e38',
                    'eRod_Autonomous_Vehicle_2024 Project'::'eRod_Autonomous_Vehicle_2024'::'Logical Architecture'::'Logical Functions'::'Root Logical Function'.'1c8eb00e-609f-4b63-a76b-87c7ff537808',
                    'eRod_Autonomous_Vehicle_2024 Project'::'eRod_Autonomous_Vehicle_2024'::'Logical Architecture'::'Logical Functions'::'Root Logical Function'.'d77bb122-0bf9-49c8-9349-3c2748585be1',
                    'eRod_Autonomous_Vehicle_2024 Project'::'eRod_Autonomous_Vehicle_2024'::'Logical Architecture'::'Logical Functions'::'Root Logical Function'.'e8eeb1b5-4b14-436d-939f-422741f61b33',
                    'eRod_Autonomous_Vehicle_2024 Project'::'eRod_Autonomous_Vehicle_2024'::'Logical Architecture'::'Logical Functions'::'Root Logical Function'.'cccc8414-558e-44b8-b776-c579e6e76e24',
                    'eRod_Autonomous_Vehicle_2024 Project'::'eRod_Autonomous_Vehicle_2024'::'Logical Architecture'::'Logical Functions'::'Root Logical Function'.'f99d3480-8396-4875-ab8d-a585b18c50b9',
                    'eRod_Autonomous_Vehicle_2024 Project'::'eRod_Autonomous_Vehicle_2024'::'Logical Architecture'::'Logical Functions'::'Root Logical Function'.'35f8b5be-612f-4161-9869-5ed9168530a1',
                    'eRod_Autonomous_Vehicle_2024 Project'::'eRod_Autonomous_Vehicle_2024'::'Logical Architecture'::'Logical Functions'::'Root Logical Function'.'a12b9128-eb74-493c-9720-4f801a24d6a6',
                    'eRod_Autonomous_Vehicle_2024 Project'::'eRod_Autonomous_Vehicle_2024'::'Logical Architecture'::'Logical Functions'::'Root Logical Function'.'20d0cafd-e854-4bae-bf97-788b841ea877',
                    'eRod_Autonomous_Vehicle_2024 Project'::'eRod_Autonomous_Vehicle_2024'::'Logical Architecture'::'Logical Functions'::'Root Logical Function'.'0c5c6960-d5fb-4270-84e1-f3c7076e9fa6',
                    'eRod_Autonomous_Vehicle_2024 Project'::'eRod_Autonomous_Vehicle_2024'::'Logical Architecture'::'Logical Functions'::'Root Logical Function'.'362d23cd-3e2a-4128-8134-4de34e796267',
                    'eRod_Autonomous_Vehicle_2024 Project'::'eRod_Autonomous_Vehicle_2024'::'Logical Architecture'::'Logical Functions'::'Root Logical Function'.'c905054d-b98e-4384-87a6-f57316e76bce',
                    'eRod_Autonomous_Vehicle_2024 Project'::'eRod_Autonomous_Vehicle_2024'::'Logical Architecture'::'Logical Functions'::'Root Logical Function'.'f5775666-3fe5-4d81-ae2b-808ebaa505f0',
                    'eRod_Autonomous_Vehicle_2024 Project'::'eRod_Autonomous_Vehicle_2024'::'Logical Architecture'::'Logical Functions'::'Root Logical Function'.'708ee609-2bcc-471e-b075-8663624694de',
                    'eRod_Autonomous_Vehicle_2024 Project'::'eRod_Autonomous_Vehicle_2024'::'Logical Architecture'::'Logical Functions'::'Root Logical Function'.'37abed24-fb61-4717-a92b-495289ca28f4',
                    'eRod_Autonomous_Vehicle_2024 Project'::'eRod_Autonomous_Vehicle_2024'::'Logical Architecture'::'Logical Functions'::'Root Logical Function'.'86e994e6-d19d-4d9f-8dea-84ea5c0194d1',
                    'eRod_Autonomous_Vehicle_2024 Project'::'eRod_Autonomous_Vehicle_2024'::'Logical Architecture'::'Logical Functions'::'Root Logical Function'.'1f954280-14ee-4c64-a4f8-6a722766dd58',
                    'eRod_Autonomous_Vehicle_2024 Project'::'eRod_Autonomous_Vehicle_2024'::'Logical Architecture'::'Logical Functions'::'Root Logical Function'.'5fa82096-df2f-4d9a-bceb-b6b4e1866e93',
                    'eRod_Autonomous_Vehicle_2024 Project'::'eRod_Autonomous_Vehicle_2024'::'Logical Architecture'::'Logical Functions'::'Root Logical Function'.'26c2d556-5c53-4b1b-a5e6-a691d6ca7dc8',
                    'eRod_Autonomous_Vehicle_2024 Project'::'eRod_Autonomous_Vehicle_2024'::'Logical Architecture'::'Logical Functions'::'Root Logical Function'.'bb415348-75cd-4b1e-b9d0-f393c2124d76',
                    'eRod_Autonomous_Vehicle_2024 Project'::'eRod_Autonomous_Vehicle_2024'::'Logical Architecture'::'Logical Functions'::'Root Logical Function'.'ad90c096-f90e-448d-ab03-d36b07193c43',
                    'eRod_Autonomous_Vehicle_2024 Project'::'eRod_Autonomous_Vehicle_2024'::'Logical Architecture'::'Logical Functions'::'Root Logical Function'.'cb3b19d6-7498-488e-9920-00d4f86b6468',
                    'eRod_Autonomous_Vehicle_2024 Project'::'eRod_Autonomous_Vehicle_2024'::'Logical Architecture'::'Logical Functions'::'Root Logical Function'.'edd168dc-8fa2-4b10-a831-c8e652921b81',
                    'eRod_Autonomous_Vehicle_2024 Project'::'eRod_Autonomous_Vehicle_2024'::'Logical Architecture'::'Logical Functions'::'Root Logical Function'.'5dfbe0c6-02fa-45b2-a988-7fb509b1ea5f',
                    'eRod_Autonomous_Vehicle_2024 Project'::'eRod_Autonomous_Vehicle_2024'::'Logical Architecture'::'Logical Functions'::'Root Logical Function'.'b49f2437-ed61-4892-b964-64704b020ac3',
                    'eRod_Autonomous_Vehicle_2024 Project'::'eRod_Autonomous_Vehicle_2024'::'Logical Architecture'::'Logical Functions'::'Root Logical Function'.'a57e94d5-e777-4b4c-aa5f-ac2d8595ac03',
                    'eRod_Autonomous_Vehicle_2024 Project'::'eRod_Autonomous_Vehicle_2024'::'Logical Architecture'::'Logical Functions'::'Root Logical Function'.'4de49d8e-32ac-4c58-804a-16d3f40ee573',
                    'eRod_Autonomous_Vehicle_2024 Project'::'eRod_Autonomous_Vehicle_2024'::'Logical Architecture'::'Logical Functions'::'Root Logical Function'.'a59d2706-68ee-49d5-9dcc-1fe46eaaac5d',
                    'eRod_Autonomous_Vehicle_2024 Project'::'eRod_Autonomous_Vehicle_2024'::'Logical Architecture'::'Logical Functions'::'Root Logical Function'.'8538b361-062a-4f5b-9074-620d0f223882',
                    'eRod_Autonomous_Vehicle_2024 Project'::'eRod_Autonomous_Vehicle_2024'::'Logical Architecture'::'Logical Functions'::'Root Logical Function'.'a5ebfdbf-73c1-4d59-862b-88888f9d7104',
                    'eRod_Autonomous_Vehicle_2024 Project'::'eRod_Autonomous_Vehicle_2024'::'Logical Architecture'::'Logical Functions'::'Root Logical Function'.'d18a222b-3410-46f6-a2c5-3b0367587d3a',
                    'eRod_Autonomous_Vehicle_2024 Project'::'eRod_Autonomous_Vehicle_2024'::'Logical Architecture'::'Logical Functions'::'Root Logical Function'.'87b8ca06-8640-467a-acf3-2885332412f6',
                    'eRod_Autonomous_Vehicle_2024 Project'::'eRod_Autonomous_Vehicle_2024'::'Logical Architecture'::'Logical Functions'::'Root Logical Function'.'cef1d025-c3a0-42bb-88c0-9916d1773272',
                    'eRod_Autonomous_Vehicle_2024 Project'::'eRod_Autonomous_Vehicle_2024'::'Logical Architecture'::'Logical Functions'::'Root Logical Function'.'9f372622-48b8-4830-944f-8ee72350a823',
                    'eRod_Autonomous_Vehicle_2024 Project'::'eRod_Autonomous_Vehicle_2024'::'Logical Architecture'::'Logical Functions'::'Root Logical Function'.'1d2d957e-522b-46de-9966-9b91c4836e11',
                    'eRod_Autonomous_Vehicle_2024 Project'::'eRod_Autonomous_Vehicle_2024'::'Logical Architecture'::'Logical Functions'::'Root Logical Function'.'5b797939-566e-4e8d-967f-5a613f57fcdf',
                    'eRod_Autonomous_Vehicle_2024 Project'::'eRod_Autonomous_Vehicle_2024'::'Logical Architecture'::'Logical Functions'::'Root Logical Function'.'e8a1b447-aae8-462f-83d2-e68efe8d3ed1',
                    'eRod_Autonomous_Vehicle_2024 Project'::'eRod_Autonomous_Vehicle_2024'::'Logical Architecture'::'Logical Functions'::'Root Logical Function'.'5684217c-ef08-4a13-a10f-2be25d9ef9bf',
                    'eRod_Autonomous_Vehicle_2024 Project'::'eRod_Autonomous_Vehicle_2024'::'Logical Architecture'::'Logical Functions'::'Root Logical Function'.'94b73d74-b009-4feb-8fe1-ab408ade5c40',
                    'eRod_Autonomous_Vehicle_2024 Project'::'eRod_Autonomous_Vehicle_2024'::'Logical Architecture'::'Logical Functions'::'Root Logical Function'.'774ae67e-2aeb-4f3a-8957-c8211a532afe',
                    'eRod_Autonomous_Vehicle_2024 Project'::'eRod_Autonomous_Vehicle_2024'::'Logical Architecture'::'Logical Functions'::'Root Logical Function'.'1cf337b5-07c4-4d1e-91a1-033468b049db',
                    'eRod_Autonomous_Vehicle_2024 Project'::'eRod_Autonomous_Vehicle_2024'::'Logical Architecture'::'Logical Functions'::'Root Logical Function'.'4f4af8a7-2552-44e8-8765-3c593ad81912',
                    'eRod_Autonomous_Vehicle_2024 Project'::'eRod_Autonomous_Vehicle_2024'::'Logical Architecture'::'Logical Functions'::'Root Logical Function'.'73c0fd18-6786-4434-9f4c-6eec548197c5',
                    'eRod_Autonomous_Vehicle_2024 Project'::'eRod_Autonomous_Vehicle_2024'::'Logical Architecture'::'Logical Functions'::'Root Logical Function'.'6dcb3416-8c5a-458c-875a-cd995816b985',
                    'eRod_Autonomous_Vehicle_2024 Project'::'eRod_Autonomous_Vehicle_2024'::'Logical Architecture'::'Logical Functions'::'Root Logical Function'.'2659f7a0-916a-49ea-9d12-eab9a18e2a75',
                    'eRod_Autonomous_Vehicle_2024 Project'::'eRod_Autonomous_Vehicle_2024'::'Logical Architecture'::'Logical Functions'::'Root Logical Function'.'fe17c8d3-e8bb-40ed-bd81-e495271faa01',
                    'eRod_Autonomous_Vehicle_2024 Project'::'eRod_Autonomous_Vehicle_2024'::'Logical Architecture'::'Logical Functions'::'Root Logical Function'.'b098fdef-75c1-4260-9be0-dbeb589d16a8',
                    'eRod_Autonomous_Vehicle_2024 Project'::'eRod_Autonomous_Vehicle_2024'::'Logical Architecture'::'Logical Functions'::'Root Logical Function'.'3af06698-4776-404e-a311-2894e5f52113',
                    'eRod_Autonomous_Vehicle_2024 Project'::'eRod_Autonomous_Vehicle_2024'::'Logical Architecture'::'Logical Functions'::'Root Logical Function'.'1d236bc3-39f0-43d8-8426-1cf5bd694aac',
                    'eRod_Autonomous_Vehicle_2024 Project'::'eRod_Autonomous_Vehicle_2024'::'Logical Architecture'::'Logical Functions'::'Root Logical Function'.'af8edaa5-bd3e-4221-867b-3e330b16bbb7',
                    'eRod_Autonomous_Vehicle_2024 Project'::'eRod_Autonomous_Vehicle_2024'::'Logical Architecture'::'Logical Functions'::'Root Logical Function'.'d3d4eea1-564e-445c-9607-1f49df308576',
                    'eRod_Autonomous_Vehicle_2024 Project'::'eRod_Autonomous_Vehicle_2024'::'Logical Architecture'::'Logical Functions'::'Root Logical Function'.'1ddea015-744f-44e6-916e-f1d14e574e03',
                    'eRod_Autonomous_Vehicle_2024 Project'::'eRod_Autonomous_Vehicle_2024'::'Logical Architecture'::'Logical Functions'::'Root Logical Function'.'ad62812e-8343-4a76-9456-0dc6ff29d0d0',
                    'eRod_Autonomous_Vehicle_2024 Project'::'eRod_Autonomous_Vehicle_2024'::'Logical Architecture'::'Logical Functions'::'Root Logical Function'.'2a699126-b079-4636-a460-b105a20b3c76',
                    'eRod_Autonomous_Vehicle_2024 Project'::'eRod_Autonomous_Vehicle_2024'::'Logical Architecture'::'Logical Functions'::'Root Logical Function'.'b95fdec6-d105-465f-9f2c-3a586cd5a624',
                    'eRod_Autonomous_Vehicle_2024 Project'::'eRod_Autonomous_Vehicle_2024'::'Logical Architecture'::'Logical Functions'::'Root Logical Function'.'ae4ff77f-fec6-4f85-bbe6-cade3bb35824',
                    'eRod_Autonomous_Vehicle_2024 Project'::'eRod_Autonomous_Vehicle_2024'::'Logical Architecture'::'Logical Functions'::'Root Logical Function'.'bf6038d4-313e-4be9-b94c-1d69db48b20f',
                    'eRod_Autonomous_Vehicle_2024 Project'::'eRod_Autonomous_Vehicle_2024'::'Logical Architecture'::'Logical Functions'::'Root Logical Function'.'063a9be7-765d-4a01-a4af-024d87dfc0f7',
                    'eRod_Autonomous_Vehicle_2024 Project'::'eRod_Autonomous_Vehicle_2024'::'Logical Architecture'::'Logical Functions'::'Root Logical Function'.'301bd8ac-cfac-4b29-ad12-48ea68fcef3e',
                    'eRod_Autonomous_Vehicle_2024 Project'::'eRod_Autonomous_Vehicle_2024'::'Logical Architecture'::'Logical Functions'::'Root Logical Function'.'3ffc52b3-84cc-4e46-b9a1-73b4477f0db4',
                    'eRod_Autonomous_Vehicle_2024 Project'::'eRod_Autonomous_Vehicle_2024'::'Logical Architecture'::'Logical Functions'::'Root Logical Function'.'065c228b-18bd-43b7-818c-46cd338ea62c',
                    'eRod_Autonomous_Vehicle_2024 Project'::'eRod_Autonomous_Vehicle_2024'::'Logical Architecture'::'Logical Functions'::'Root Logical Function'.'93262ba9-6596-4b5f-b46b-4fd1ddf0d744',
                    'eRod_Autonomous_Vehicle_2024 Project'::'eRod_Autonomous_Vehicle_2024'::'Logical Architecture'::'Logical Functions'::'Root Logical Function'.'1dfbf83d-de25-4e27-8ccb-e14f31c3d4bd',
                    'eRod_Autonomous_Vehicle_2024 Project'::'eRod_Autonomous_Vehicle_2024'::'Logical Architecture'::'Logical Functions'::'Root Logical Function'.'3100499d-8657-4e28-a511-cf0fb745cfc4',
                    'eRod_Autonomous_Vehicle_2024 Project'::'eRod_Autonomous_Vehicle_2024'::'Logical Architecture'::'Logical Functions'::'Root Logical Function'.'d096cac7-97a3-419f-b943-1af03c0794a9',
                    'eRod_Autonomous_Vehicle_2024 Project'::'eRod_Autonomous_Vehicle_2024'::'Logical Architecture'::'Logical Functions'::'Root Logical Function'.'418ee4a5-2399-474b-be28-1165c851f3d6',
                    'eRod_Autonomous_Vehicle_2024 Project'::'eRod_Autonomous_Vehicle_2024'::'Logical Architecture'::'Logical Functions'::'Root Logical Function'.'66d79c3e-9600-4eb7-9163-a41a826a1eb7',
                    'eRod_Autonomous_Vehicle_2024 Project'::'eRod_Autonomous_Vehicle_2024'::'Logical Architecture'::'Logical Functions'::'Root Logical Function'.'f556bb6e-428a-4906-ba9f-e0b9b35648e1',
                    'eRod_Autonomous_Vehicle_2024 Project'::'eRod_Autonomous_Vehicle_2024'::'Logical Architecture'::'Logical Functions'::'Root Logical Function'.'033494da-7516-44f8-a2d3-007f5e9f12cd'); 
                     
                }  
            } 
            package  'Structure' {
                @PackageMeta {
                    type = "LogicalComponentPkg";
                } 
                @CapellaID { eid = "22af669d-f8e4-437b-bd40-36c242551be4"; } 
                part 'eRod System' : LogicalComponent { 
                    @CapellaID { eid = "c4a13129-c11b-4c27-8b4e-476f02de66b9"; } 
                    attribute :>> isAbstract = false; 
                    attribute :>> isActor = false; 
                    attribute :>> isHuman = false; 
                    allocation '48d70b70-2342-4858-b6ec-7de8102695d6' : ComponentFunctionalAllocation
                        allocate function ::> 'eRod_Autonomous_Vehicle_2024 Project'::'eRod_Autonomous_Vehicle_2024'::'Logical Architecture'::'Logical Functions'::'Root Logical Function'.'Motor Start'
                        to component ::> 'eRod_Autonomous_Vehicle_2024 Project'::'eRod_Autonomous_Vehicle_2024'::'Logical Architecture'::'Structure'::'eRod System';
                    perform 'eRod_Autonomous_Vehicle_2024 Project'::'eRod_Autonomous_Vehicle_2024'::'Logical Architecture'::'Logical Functions'::'Root Logical Function'.'Motor Start' ; 
                    allocation 'f7b18b86-989d-4ab7-9697-f0f6aef56147' : ComponentFunctionalAllocation
                        allocate function ::> 'eRod_Autonomous_Vehicle_2024 Project'::'eRod_Autonomous_Vehicle_2024'::'Logical Architecture'::'Logical Functions'::'Root Logical Function'.'Deaccelerate'
                        to component ::> 'eRod_Autonomous_Vehicle_2024 Project'::'eRod_Autonomous_Vehicle_2024'::'Logical Architecture'::'Structure'::'eRod System';
                    perform 'eRod_Autonomous_Vehicle_2024 Project'::'eRod_Autonomous_Vehicle_2024'::'Logical Architecture'::'Logical Functions'::'Root Logical Function'.'Deaccelerate' ; 
                    allocation '0a479dbb-a597-4f28-8629-99b63efade93' : ComponentFunctionalAllocation
                        allocate function ::> 'eRod_Autonomous_Vehicle_2024 Project'::'eRod_Autonomous_Vehicle_2024'::'Logical Architecture'::'Logical Functions'::'Root Logical Function'.'Stop'
                        to component ::> 'eRod_Autonomous_Vehicle_2024 Project'::'eRod_Autonomous_Vehicle_2024'::'Logical Architecture'::'Structure'::'eRod System';
                    perform 'eRod_Autonomous_Vehicle_2024 Project'::'eRod_Autonomous_Vehicle_2024'::'Logical Architecture'::'Logical Functions'::'Root Logical Function'.'Stop' ; 
                    allocation 'da5f5810-e58c-403b-919e-118cf118fe09' : ComponentFunctionalAllocation
                        allocate function ::> 'eRod_Autonomous_Vehicle_2024 Project'::'eRod_Autonomous_Vehicle_2024'::'Logical Architecture'::'Logical Functions'::'Root Logical Function'.'Motor overheating warning '
                        to component ::> 'eRod_Autonomous_Vehicle_2024 Project'::'eRod_Autonomous_Vehicle_2024'::'Logical Architecture'::'Structure'::'eRod System';
                    perform 'eRod_Autonomous_Vehicle_2024 Project'::'eRod_Autonomous_Vehicle_2024'::'Logical Architecture'::'Logical Functions'::'Root Logical Function'.'Motor overheating warning ' ; 
                    allocation '447a813a-c372-45f1-8285-fc3cc1077fe6' : ComponentFunctionalAllocation
                        allocate function ::> 'eRod_Autonomous_Vehicle_2024 Project'::'eRod_Autonomous_Vehicle_2024'::'Logical Architecture'::'Logical Functions'::'Root Logical Function'.'Sporty drive'
                        to component ::> 'eRod_Autonomous_Vehicle_2024 Project'::'eRod_Autonomous_Vehicle_2024'::'Logical Architecture'::'Structure'::'eRod System';
                    perform 'eRod_Autonomous_Vehicle_2024 Project'::'eRod_Autonomous_Vehicle_2024'::'Logical Architecture'::'Logical Functions'::'Root Logical Function'.'Sporty drive' ; 
                    port 'Command' : ComponentPort { 
                        @CapellaID { eid = "82091bf9-0546-4221-88b2-9958e108c972"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::INOUT; 
                        attribute :>> isUnique = false; 
                    }  
                    port 'Power' : ComponentPort { 
                        @CapellaID { eid = "d74a5ac8-dcfd-43b6-b9c3-ac2da5c00929"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::INOUT; 
                        attribute :>> isUnique = false; 
                    }  
                    port 'Exp' : ComponentPort { 
                        @CapellaID { eid = "b88d9876-e8ae-4c56-9e54-a22954b3b78c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                    }  
                    port 'Info' : ComponentPort { 
                        @CapellaID { eid = "5e517538-5562-4a40-b9a1-56f1e687530d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                    }  
                    port 'Sit' : ComponentPort { 
                        @CapellaID { eid = "4c7f942c-f021-474c-8077-d3241479bd20"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                    }  
                    port 'Temp' : ComponentPort { 
                        @CapellaID { eid = "cc8d9f54-309f-4f2d-9b1d-d6f0d6f3a290"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                    }  
                    interface 'c097bdf7-2737-4cf6-b21d-b8a04bdf7027' : ComponentExchange 
                        connect source ::> 'eRod_Autonomous_Vehicle_2024 Project'::'eRod_Autonomous_Vehicle_2024'::'Logical Architecture'::'Structure'::'eRod System'.'Battery System'.'Battery'.'CP 1'
                        to  target ::> 'eRod_Autonomous_Vehicle_2024 Project'::'eRod_Autonomous_Vehicle_2024'::'Logical Architecture'::'Structure'::'eRod System'.'Auxiliary Consumers'.'CP 1' { 
                        @CapellaID { eid = "c097bdf7-2737-4cf6-b21d-b8a04bdf7027"; } 
                        attribute :>> kind = ComponentExchangeKind::FLOW; 
                        attribute :>> interfaceName = "Energy"; 
                        attribute :>> isOriented = false; 
                    }  
                    interface '6800b945-167d-41f6-bc15-64e1ce776702' : ComponentExchange 
                        connect source ::> 'eRod_Autonomous_Vehicle_2024 Project'::'eRod_Autonomous_Vehicle_2024'::'Logical Architecture'::'Structure'::'eRod System'.'Battery System'.'Battery'.'Battery to Motor'
                        to  target ::> 'eRod_Autonomous_Vehicle_2024 Project'::'eRod_Autonomous_Vehicle_2024'::'Logical Architecture'::'Structure'::'eRod System'.'Powertrain'.'Electric motor'.'Motor from Battery' { 
                        @CapellaID { eid = "6800b945-167d-41f6-bc15-64e1ce776702"; } 
                        attribute :>> kind = ComponentExchangeKind::FLOW; 
                        attribute :>> interfaceName = "Energy"; 
                        attribute :>> isOriented = false; 
                        ref :>> convoyedInformations =  ('eRod_Autonomous_Vehicle_2024 Project'::'eRod_Autonomous_Vehicle_2024'::'Logical Architecture'::'Data'::'Electricity'); 
                    }  
                    interface 'e341d16c-5a6f-4b0b-9051-c75525d48151' : ComponentExchange 
                        connect source ::> 'eRod_Autonomous_Vehicle_2024 Project'::'eRod_Autonomous_Vehicle_2024'::'Logical Architecture'::'Structure'::'eRod System'.'Power'
                        to  target ::> 'eRod_Autonomous_Vehicle_2024 Project'::'eRod_Autonomous_Vehicle_2024'::'Logical Architecture'::'Structure'::'eRod System'.'Powertrain'.'CP 4' { 
                        @CapellaID { eid = "e341d16c-5a6f-4b0b-9051-c75525d48151"; } 
                        attribute :>> kind = ComponentExchangeKind::FLOW; 
                        attribute :>> interfaceName = "Power"; 
                        attribute :>> isOriented = false; 
                    }  
                    interface 'ec8c564d-cc27-403a-b6de-c2ed7ed23a17' : ComponentExchange 
                        connect source ::> 'eRod_Autonomous_Vehicle_2024 Project'::'eRod_Autonomous_Vehicle_2024'::'Logical Architecture'::'Structure'::'eRod System'.'Powertrain'.'CP 3'
                        to  target ::> 'eRod_Autonomous_Vehicle_2024 Project'::'eRod_Autonomous_Vehicle_2024'::'Logical Architecture'::'Structure'::'eRod System'.'Command' { 
                        @CapellaID { eid = "ec8c564d-cc27-403a-b6de-c2ed7ed23a17"; } 
                        attribute :>> kind = ComponentExchangeKind::FLOW; 
                        attribute :>> interfaceName = "Command"; 
                        attribute :>> isOriented = false; 
                    }  
                    part 'Auxiliary Consumers' : LogicalComponent { 
                        @CapellaID { eid = "ee3e2bf7-d896-4502-9a6f-7fac8e63ffbd"; } 
                        attribute :>> isAbstract = false; 
                        attribute :>> isActor = false; 
                        attribute :>> isHuman = false; 
                        port 'CP 1' : ComponentPort { 
                            @CapellaID { eid = "7a3f147d-75a1-47bb-966a-7f4074ca8fc4"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                        }  
                    }  
                    part 'Powertrain' : LogicalComponent { 
                        @CapellaID { eid = "1eb9b52d-571f-4348-a342-3c0edd04b7c8"; } 
                        attribute :>> isAbstract = false; 
                        attribute :>> isActor = false; 
                        attribute :>> isHuman = false; 
                        port 'CP 6' : ComponentPort { 
                            @CapellaID { eid = "f6ab62b8-ccff-41c4-9d6d-c65744cbdf10"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                        }  
                        port 'CP 4' : ComponentPort { 
                            @CapellaID { eid = "936926f5-0c8f-451f-a6a9-6d38228483b8"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::INOUT; 
                            attribute :>> isUnique = false; 
                        }  
                        port 'CP 3' : ComponentPort { 
                            @CapellaID { eid = "0956cb81-2d69-454b-90cb-849df021e185"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::INOUT; 
                            attribute :>> isUnique = false; 
                        }  
                        interface 'e05e5cb1-7c80-4d09-bad0-728fed629e52' : ComponentExchange 
                            connect source ::> 'eRod_Autonomous_Vehicle_2024 Project'::'eRod_Autonomous_Vehicle_2024'::'Logical Architecture'::'Structure'::'eRod System'.'Powertrain'.'CP 6'
                            to  target ::> 'eRod_Autonomous_Vehicle_2024 Project'::'eRod_Autonomous_Vehicle_2024'::'Logical Architecture'::'Structure'::'eRod System'.'Powertrain'.'Transmission'.'CP 1' { 
                            @CapellaID { eid = "e05e5cb1-7c80-4d09-bad0-728fed629e52"; } 
                            attribute :>> kind = ComponentExchangeKind::FLOW; 
                            attribute :>> interfaceName = "Torque"; 
                            attribute :>> isOriented = false; 
                        }  
                        interface 'c94df1bf-1884-4565-9f7f-bbb958d684f3' : ComponentExchange 
                            connect source ::> 'eRod_Autonomous_Vehicle_2024 Project'::'eRod_Autonomous_Vehicle_2024'::'Logical Architecture'::'Structure'::'eRod System'.'Powertrain'.'Transmission'.'CP 2'
                            to  target ::> 'eRod_Autonomous_Vehicle_2024 Project'::'eRod_Autonomous_Vehicle_2024'::'Logical Architecture'::'Structure'::'eRod System'.'Powertrain'.'Axies'.'CP 1' { 
                            @CapellaID { eid = "c94df1bf-1884-4565-9f7f-bbb958d684f3"; } 
                            attribute :>> kind = ComponentExchangeKind::FLOW; 
                            attribute :>> interfaceName = "Torque"; 
                            attribute :>> isOriented = false; 
                        }  
                        interface '8a142a49-ae17-4ee6-a80a-5180c9dc9ea6' : ComponentExchange 
                            connect source ::> 'eRod_Autonomous_Vehicle_2024 Project'::'eRod_Autonomous_Vehicle_2024'::'Logical Architecture'::'Structure'::'eRod System'.'Powertrain'.'Electric motor'.'Motor to ECU'
                            to  target ::> 'eRod_Autonomous_Vehicle_2024 Project'::'eRod_Autonomous_Vehicle_2024'::'Logical Architecture'::'Structure'::'eRod System'.'Powertrain'.'ECU'.'Temperature controll unit'.'Temperature from Motor' { 
                            @CapellaID { eid = "8a142a49-ae17-4ee6-a80a-5180c9dc9ea6"; } 
                            attribute :>> kind = ComponentExchangeKind::FLOW; 
                            attribute :>> interfaceName = "Temperature"; 
                            attribute :>> isOriented = false; 
                            ref :>> convoyedInformations =  ('eRod_Autonomous_Vehicle_2024 Project'::'eRod_Autonomous_Vehicle_2024'::'Logical Architecture'::'Data'::'Temperature'); 
                        }  
                        interface 'bdcf9155-e91b-46ee-8c79-b9da51929203' : ComponentExchange 
                            connect source ::> 'eRod_Autonomous_Vehicle_2024 Project'::'eRod_Autonomous_Vehicle_2024'::'Logical Architecture'::'Structure'::'eRod System'.'Powertrain'.'Electric motor'.'CP 5'
                            to  target ::> 'eRod_Autonomous_Vehicle_2024 Project'::'eRod_Autonomous_Vehicle_2024'::'Logical Architecture'::'Structure'::'eRod System'.'Powertrain'.'ECU'.'CP 4' { 
                            @CapellaID { eid = "bdcf9155-e91b-46ee-8c79-b9da51929203"; } 
                            attribute :>> kind = ComponentExchangeKind::FLOW; 
                            attribute :>> interfaceName = "Information"; 
                            attribute :>> isOriented = false; 
                        }  
                        part 'Electric motor' : LogicalComponent { 
                            @CapellaID { eid = "96153ae3-48df-4008-80ab-da80d9cb0d92"; } 
                            attribute :>> isAbstract = false; 
                            attribute :>> isActor = false; 
                            attribute :>> isHuman = false; 
                            allocation '21ff7a08-e668-4cb9-818b-0fdb4a87bb15' : ComponentFunctionalAllocation
                                allocate function ::> 'eRod_Autonomous_Vehicle_2024 Project'::'eRod_Autonomous_Vehicle_2024'::'Logical Architecture'::'Logical Functions'::'Root Logical Function'.'Transfer Energy'.'Generate heat'
                                to component ::> 'eRod_Autonomous_Vehicle_2024 Project'::'eRod_Autonomous_Vehicle_2024'::'Logical Architecture'::'Structure'::'eRod System'.'Powertrain'.'Electric motor';
                            perform 'eRod_Autonomous_Vehicle_2024 Project'::'eRod_Autonomous_Vehicle_2024'::'Logical Architecture'::'Logical Functions'::'Root Logical Function'.'Transfer Energy'.'Generate heat' ; 
                            allocation '86721a89-106b-4581-9349-ebfc235565d2' : ComponentFunctionalAllocation
                                allocate function ::> 'eRod_Autonomous_Vehicle_2024 Project'::'eRod_Autonomous_Vehicle_2024'::'Logical Architecture'::'Logical Functions'::'Root Logical Function'.'Transfer Energy'.'Tranfer electrical energy into mechanical energy'
                                to component ::> 'eRod_Autonomous_Vehicle_2024 Project'::'eRod_Autonomous_Vehicle_2024'::'Logical Architecture'::'Structure'::'eRod System'.'Powertrain'.'Electric motor';
                            perform 'eRod_Autonomous_Vehicle_2024 Project'::'eRod_Autonomous_Vehicle_2024'::'Logical Architecture'::'Logical Functions'::'Root Logical Function'.'Transfer Energy'.'Tranfer electrical energy into mechanical energy' ; 
                            port 'CP 5' : ComponentPort { 
                                @CapellaID { eid = "24d6a819-bbe8-4c91-b29b-2b6c0488d84d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::INOUT; 
                                attribute :>> isUnique = false; 
                            }  
                            port 'Motor from Battery' : ComponentPort { 
                                @CapellaID { eid = "91d9a69e-3a7b-40b6-94a7-9b5a583a25cc"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                                ref :>> requiredInterfaces =  ('eRod_Autonomous_Vehicle_2024 Project'::'eRod_Autonomous_Vehicle_2024'::'Logical Architecture'::'Interfaces'::'Electricity'); 
                            }  
                            port 'Motor to ECU' : ComponentPort { 
                                @CapellaID { eid = "df8fa465-cd34-45b3-a8dc-3f8980098272"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref :>> providedInterfaces =  ('eRod_Autonomous_Vehicle_2024 Project'::'eRod_Autonomous_Vehicle_2024'::'Logical Architecture'::'Interfaces'::'Temperature'); 
                            }  
                            port 'Motor to Environment' : ComponentPort { 
                                @CapellaID { eid = "25e2df12-8b0a-4ed6-a720-20fa48ffb849"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref :>> providedInterfaces =  ('eRod_Autonomous_Vehicle_2024 Project'::'eRod_Autonomous_Vehicle_2024'::'Logical Architecture'::'Interfaces'::'Heat'); 
                            }  
                            part 'Rotor' : LogicalComponent { 
                                @CapellaID { eid = "0da1ddb7-7f23-48b4-be4a-05b971797fbc"; } 
                                attribute :>> isAbstract = false; 
                                attribute :>> isActor = false; 
                                attribute :>> isHuman = false; 
                                allocation 'c7bc7698-355b-498f-b5ef-fd2609947ddd' : ComponentFunctionalAllocation
                                    allocate function ::> 'eRod_Autonomous_Vehicle_2024 Project'::'eRod_Autonomous_Vehicle_2024'::'Logical Architecture'::'Logical Functions'::'Root Logical Function'.'deliver mechanical power'
                                    to component ::> 'eRod_Autonomous_Vehicle_2024 Project'::'eRod_Autonomous_Vehicle_2024'::'Logical Architecture'::'Structure'::'eRod System'.'Powertrain'.'Electric motor'.'Rotor';
                                perform 'eRod_Autonomous_Vehicle_2024 Project'::'eRod_Autonomous_Vehicle_2024'::'Logical Architecture'::'Logical Functions'::'Root Logical Function'.'deliver mechanical power' ; 
                                allocation '869acbf8-ae4f-411b-b443-37fa7125be81' : ComponentFunctionalAllocation
                                    allocate function ::> 'eRod_Autonomous_Vehicle_2024 Project'::'eRod_Autonomous_Vehicle_2024'::'Logical Architecture'::'Logical Functions'::'Root Logical Function'.'Generate heat (Rotor)'
                                    to component ::> 'eRod_Autonomous_Vehicle_2024 Project'::'eRod_Autonomous_Vehicle_2024'::'Logical Architecture'::'Structure'::'eRod System'.'Powertrain'.'Electric motor'.'Rotor';
                                perform 'eRod_Autonomous_Vehicle_2024 Project'::'eRod_Autonomous_Vehicle_2024'::'Logical Architecture'::'Logical Functions'::'Root Logical Function'.'Generate heat (Rotor)' ; 
                                allocation '9f5d45f2-af5c-4850-bc44-0a11fa1c5f24' : ComponentFunctionalAllocation
                                    allocate function ::> 'eRod_Autonomous_Vehicle_2024 Project'::'eRod_Autonomous_Vehicle_2024'::'Logical Architecture'::'Logical Functions'::'Root Logical Function'.'Gather 21'
                                    to component ::> 'eRod_Autonomous_Vehicle_2024 Project'::'eRod_Autonomous_Vehicle_2024'::'Logical Architecture'::'Structure'::'eRod System'.'Powertrain'.'Electric motor'.'Rotor';
                                perform 'eRod_Autonomous_Vehicle_2024 Project'::'eRod_Autonomous_Vehicle_2024'::'Logical Architecture'::'Logical Functions'::'Root Logical Function'.'Gather 21' ; 
                                allocation 'ff0ce619-d0d4-4825-92c7-8b2ba2ee5a9b' : ComponentFunctionalAllocation
                                    allocate function ::> 'eRod_Autonomous_Vehicle_2024 Project'::'eRod_Autonomous_Vehicle_2024'::'Logical Architecture'::'Logical Functions'::'Root Logical Function'.'Transfer Energy'.'Acquire electrical Energy'
                                    to component ::> 'eRod_Autonomous_Vehicle_2024 Project'::'eRod_Autonomous_Vehicle_2024'::'Logical Architecture'::'Structure'::'eRod System'.'Powertrain'.'Electric motor'.'Rotor';
                                perform 'eRod_Autonomous_Vehicle_2024 Project'::'eRod_Autonomous_Vehicle_2024'::'Logical Architecture'::'Logical Functions'::'Root Logical Function'.'Transfer Energy'.'Acquire electrical Energy' ; 
                                ref :>> ownedFunctionalAllocation =  ('eRod_Autonomous_Vehicle_2024 Project'::'eRod_Autonomous_Vehicle_2024'::'Logical Architecture'::'Structure'::'eRod System'.'Powertrain'.'Electric motor'.'Rotor'.'c7bc7698-355b-498f-b5ef-fd2609947ddd',
                                'eRod_Autonomous_Vehicle_2024 Project'::'eRod_Autonomous_Vehicle_2024'::'Logical Architecture'::'Structure'::'eRod System'.'Powertrain'.'Electric motor'.'Rotor'.'869acbf8-ae4f-411b-b443-37fa7125be81',
                                'eRod_Autonomous_Vehicle_2024 Project'::'eRod_Autonomous_Vehicle_2024'::'Logical Architecture'::'Structure'::'eRod System'.'Powertrain'.'Electric motor'.'Rotor'.'9f5d45f2-af5c-4850-bc44-0a11fa1c5f24',
                                'eRod_Autonomous_Vehicle_2024 Project'::'eRod_Autonomous_Vehicle_2024'::'Logical Architecture'::'Structure'::'eRod System'.'Powertrain'.'Electric motor'.'Rotor'.'ff0ce619-d0d4-4825-92c7-8b2ba2ee5a9b'); 
                                 
                            }  
                            part 'Housing' : LogicalComponent { 
                                @CapellaID { eid = "6a75f0cf-68c8-4231-bd27-c5428cdf53e8"; } 
                                attribute :>> isAbstract = false; 
                                attribute :>> isActor = false; 
                                attribute :>> isHuman = false; 
                                allocation 'ad4689ed-8f13-44dd-b487-071c708aa5d6' : ComponentFunctionalAllocation
                                    allocate function ::> 'eRod_Autonomous_Vehicle_2024 Project'::'eRod_Autonomous_Vehicle_2024'::'Logical Architecture'::'Logical Functions'::'Root Logical Function'.'protect'
                                    to component ::> 'eRod_Autonomous_Vehicle_2024 Project'::'eRod_Autonomous_Vehicle_2024'::'Logical Architecture'::'Structure'::'eRod System'.'Powertrain'.'Electric motor'.'Housing';
                                perform 'eRod_Autonomous_Vehicle_2024 Project'::'eRod_Autonomous_Vehicle_2024'::'Logical Architecture'::'Logical Functions'::'Root Logical Function'.'protect' ; 
                                allocation '3e6754d7-4a96-4ef2-8586-f02d7689ada4' : ComponentFunctionalAllocation
                                    allocate function ::> 'eRod_Autonomous_Vehicle_2024 Project'::'eRod_Autonomous_Vehicle_2024'::'Logical Architecture'::'Logical Functions'::'Root Logical Function'.'Transfer heat'
                                    to component ::> 'eRod_Autonomous_Vehicle_2024 Project'::'eRod_Autonomous_Vehicle_2024'::'Logical Architecture'::'Structure'::'eRod System'.'Powertrain'.'Electric motor'.'Housing';
                                perform 'eRod_Autonomous_Vehicle_2024 Project'::'eRod_Autonomous_Vehicle_2024'::'Logical Architecture'::'Logical Functions'::'Root Logical Function'.'Transfer heat' ; 
                                ref :>> ownedFunctionalAllocation =  ('eRod_Autonomous_Vehicle_2024 Project'::'eRod_Autonomous_Vehicle_2024'::'Logical Architecture'::'Structure'::'eRod System'.'Powertrain'.'Electric motor'.'Housing'.'ad4689ed-8f13-44dd-b487-071c708aa5d6',
                                'eRod_Autonomous_Vehicle_2024 Project'::'eRod_Autonomous_Vehicle_2024'::'Logical Architecture'::'Structure'::'eRod System'.'Powertrain'.'Electric motor'.'Housing'.'3e6754d7-4a96-4ef2-8586-f02d7689ada4'); 
                                 
                            }  
                            ref :>> ownedFunctionalAllocation =  ('eRod_Autonomous_Vehicle_2024 Project'::'eRod_Autonomous_Vehicle_2024'::'Logical Architecture'::'Structure'::'eRod System'.'Powertrain'.'Electric motor'.'21ff7a08-e668-4cb9-818b-0fdb4a87bb15',
                            'eRod_Autonomous_Vehicle_2024 Project'::'eRod_Autonomous_Vehicle_2024'::'Logical Architecture'::'Structure'::'eRod System'.'Powertrain'.'Electric motor'.'86721a89-106b-4581-9349-ebfc235565d2'); 
                             
                            ref :>> ownedLogicalComponents =  ('eRod_Autonomous_Vehicle_2024 Project'::'eRod_Autonomous_Vehicle_2024'::'Logical Architecture'::'Structure'::'eRod System'.'Powertrain'.'Electric motor'.'Rotor',
                            'eRod_Autonomous_Vehicle_2024 Project'::'eRod_Autonomous_Vehicle_2024'::'Logical Architecture'::'Structure'::'eRod System'.'Powertrain'.'Electric motor'.'Housing'); 
                        }  
                        part 'Differential' : LogicalComponent { 
                            @CapellaID { eid = "486f1d8e-1cc0-4546-be24-6698847ff9ff"; } 
                            attribute :>> isAbstract = false; 
                            attribute :>> isActor = false; 
                            attribute :>> isHuman = false; 
                        }  
                        part 'Driveshafts' : LogicalComponent { 
                            @CapellaID { eid = "f8ea0203-6b1f-4f87-b031-df7f4bcc1d86"; } 
                            attribute :>> isAbstract = false; 
                            attribute :>> isActor = false; 
                            attribute :>> isHuman = false; 
                        }  
                        part 'Transmission' : LogicalComponent { 
                            @CapellaID { eid = "35ce9cb5-36dd-4687-87d6-eaa1003a83dc"; } 
                            attribute :>> isAbstract = false; 
                            attribute :>> isActor = false; 
                            attribute :>> isHuman = false; 
                            allocation '166cdb84-ad69-47c2-aa7f-ae97e6bbb96c' : ComponentFunctionalAllocation
                                allocate function ::> 'eRod_Autonomous_Vehicle_2024 Project'::'eRod_Autonomous_Vehicle_2024'::'Logical Architecture'::'Logical Functions'::'Root Logical Function'.'Transfer power to Axies'
                                to component ::> 'eRod_Autonomous_Vehicle_2024 Project'::'eRod_Autonomous_Vehicle_2024'::'Logical Architecture'::'Structure'::'eRod System'.'Powertrain'.'Transmission';
                            perform 'eRod_Autonomous_Vehicle_2024 Project'::'eRod_Autonomous_Vehicle_2024'::'Logical Architecture'::'Logical Functions'::'Root Logical Function'.'Transfer power to Axies' ; 
                            port 'CP 1' : ComponentPort { 
                                @CapellaID { eid = "f239454f-4bcb-40fa-b7f5-73f26bba439d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                            }  
                            port 'CP 2' : ComponentPort { 
                                @CapellaID { eid = "3c0d9bc3-9b2d-4d74-adc4-26d48b914486"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                            }  
                            ref :>> ownedFunctionalAllocation =  ('eRod_Autonomous_Vehicle_2024 Project'::'eRod_Autonomous_Vehicle_2024'::'Logical Architecture'::'Structure'::'eRod System'.'Powertrain'.'Transmission'.'166cdb84-ad69-47c2-aa7f-ae97e6bbb96c'); 
                        }  
                        part 'Axies' : LogicalComponent { 
                            @CapellaID { eid = "ee4432ae-cb98-4fb6-a67a-1d9af5c0623c"; } 
                            attribute :>> isAbstract = false; 
                            attribute :>> isActor = false; 
                            attribute :>> isHuman = false; 
                            allocation '8bf77608-c6d6-4373-8b11-38c161cd35bf' : ComponentFunctionalAllocation
                                allocate function ::> 'eRod_Autonomous_Vehicle_2024 Project'::'eRod_Autonomous_Vehicle_2024'::'Logical Architecture'::'Logical Functions'::'Root Logical Function'.'Apply rotation on wheels'
                                to component ::> 'eRod_Autonomous_Vehicle_2024 Project'::'eRod_Autonomous_Vehicle_2024'::'Logical Architecture'::'Structure'::'eRod System'.'Powertrain'.'Axies';
                            perform 'eRod_Autonomous_Vehicle_2024 Project'::'eRod_Autonomous_Vehicle_2024'::'Logical Architecture'::'Logical Functions'::'Root Logical Function'.'Apply rotation on wheels' ; 
                            allocation 'b1463d75-e7e5-4fb8-8791-909fe02df79b' : ComponentFunctionalAllocation
                                allocate function ::> 'eRod_Autonomous_Vehicle_2024 Project'::'eRod_Autonomous_Vehicle_2024'::'Logical Architecture'::'Logical Functions'::'Root Logical Function'.'Split 25'
                                to component ::> 'eRod_Autonomous_Vehicle_2024 Project'::'eRod_Autonomous_Vehicle_2024'::'Logical Architecture'::'Structure'::'eRod System'.'Powertrain'.'Axies';
                            perform 'eRod_Autonomous_Vehicle_2024 Project'::'eRod_Autonomous_Vehicle_2024'::'Logical Architecture'::'Logical Functions'::'Root Logical Function'.'Split 25' ; 
                            port 'CP 1' : ComponentPort { 
                                @CapellaID { eid = "8cc0df91-cf26-4adb-af81-b94cf17fae2c"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                            }  
                            ref :>> ownedFunctionalAllocation =  ('eRod_Autonomous_Vehicle_2024 Project'::'eRod_Autonomous_Vehicle_2024'::'Logical Architecture'::'Structure'::'eRod System'.'Powertrain'.'Axies'.'8bf77608-c6d6-4373-8b11-38c161cd35bf',
                            'eRod_Autonomous_Vehicle_2024 Project'::'eRod_Autonomous_Vehicle_2024'::'Logical Architecture'::'Structure'::'eRod System'.'Powertrain'.'Axies'.'b1463d75-e7e5-4fb8-8791-909fe02df79b'); 
                        }  
                        part 'ECU' : LogicalComponent { 
                            @CapellaID { eid = "544a005c-dffc-4ac2-86c9-23ec38388a0b"; } 
                            attribute :>> isAbstract = false; 
                            attribute :>> isActor = false; 
                            attribute :>> isHuman = false; 
                            port 'CP 4' : ComponentPort { 
                                @CapellaID { eid = "70910066-b1a8-47cc-bc20-b6f487764e07"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::INOUT; 
                                attribute :>> isUnique = false; 
                            }  
                            part 'Temperature controll unit' : LogicalComponent { 
                                @CapellaID { eid = "f5cfe85d-4642-4c5e-9266-f2b3a6ee5780"; } 
                                attribute :>> isAbstract = false; 
                                attribute :>> isActor = false; 
                                attribute :>> isHuman = false; 
                                allocation 'd5f60677-b61c-48f4-8a97-c20cbcf08550' : ComponentFunctionalAllocation
                                    allocate function ::> 'eRod_Autonomous_Vehicle_2024 Project'::'eRod_Autonomous_Vehicle_2024'::'Logical Architecture'::'Logical Functions'::'Root Logical Function'.'Motor protect'.'Monitor temperature'
                                    to component ::> 'eRod_Autonomous_Vehicle_2024 Project'::'eRod_Autonomous_Vehicle_2024'::'Logical Architecture'::'Structure'::'eRod System'.'Powertrain'.'ECU'.'Temperature controll unit';
                                perform 'eRod_Autonomous_Vehicle_2024 Project'::'eRod_Autonomous_Vehicle_2024'::'Logical Architecture'::'Logical Functions'::'Root Logical Function'.'Motor protect'.'Monitor temperature' ; 
                                allocation 'a8edfb76-586b-4a42-9e7a-9fdd6be4ff7c' : ComponentFunctionalAllocation
                                    allocate function ::> 'eRod_Autonomous_Vehicle_2024 Project'::'eRod_Autonomous_Vehicle_2024'::'Logical Architecture'::'Logical Functions'::'Root Logical Function'.'Motor protect'.'Detect temperature limit'
                                    to component ::> 'eRod_Autonomous_Vehicle_2024 Project'::'eRod_Autonomous_Vehicle_2024'::'Logical Architecture'::'Structure'::'eRod System'.'Powertrain'.'ECU'.'Temperature controll unit';
                                perform 'eRod_Autonomous_Vehicle_2024 Project'::'eRod_Autonomous_Vehicle_2024'::'Logical Architecture'::'Logical Functions'::'Root Logical Function'.'Motor protect'.'Detect temperature limit' ; 
                                port 'Temperature from Motor' : ComponentPort { 
                                    @CapellaID { eid = "6ce171cf-eb60-436b-ace3-dede3c1cf74f"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> kind = ComponentPortKind::FLOW; 
                                    attribute :>> isMaxInclusive = false; 
                                    attribute :>> isMinInclusive = false; 
                                    attribute :>> isOrdered = false; 
                                    attribute :>> orientation = OrientationPortKind::IN; 
                                    attribute :>> isUnique = false; 
                                    ref :>> requiredInterfaces =  ('eRod_Autonomous_Vehicle_2024 Project'::'eRod_Autonomous_Vehicle_2024'::'Logical Architecture'::'Interfaces'::'Temperature'); 
                                }  
                                ref :>> ownedFunctionalAllocation =  ('eRod_Autonomous_Vehicle_2024 Project'::'eRod_Autonomous_Vehicle_2024'::'Logical Architecture'::'Structure'::'eRod System'.'Powertrain'.'ECU'.'Temperature controll unit'.'d5f60677-b61c-48f4-8a97-c20cbcf08550',
                                'eRod_Autonomous_Vehicle_2024 Project'::'eRod_Autonomous_Vehicle_2024'::'Logical Architecture'::'Structure'::'eRod System'.'Powertrain'.'ECU'.'Temperature controll unit'.'a8edfb76-586b-4a42-9e7a-9fdd6be4ff7c'); 
                            }  
                            part 'Power controll unit' : LogicalComponent { 
                                @CapellaID { eid = "18242118-0d7b-4cf9-9099-8189b66785d1"; } 
                                attribute :>> isAbstract = false; 
                                attribute :>> isActor = false; 
                                attribute :>> isHuman = false; 
                                allocation 'e330d57c-24f9-4005-b690-cc06e628421d' : ComponentFunctionalAllocation
                                    allocate function ::> 'eRod_Autonomous_Vehicle_2024 Project'::'eRod_Autonomous_Vehicle_2024'::'Logical Architecture'::'Logical Functions'::'Root Logical Function'.'Motor protect'.'Reduce power'
                                    to component ::> 'eRod_Autonomous_Vehicle_2024 Project'::'eRod_Autonomous_Vehicle_2024'::'Logical Architecture'::'Structure'::'eRod System'.'Powertrain'.'ECU'.'Power controll unit';
                                perform 'eRod_Autonomous_Vehicle_2024 Project'::'eRod_Autonomous_Vehicle_2024'::'Logical Architecture'::'Logical Functions'::'Root Logical Function'.'Motor protect'.'Reduce power' ; 
                                allocation '17e2931c-52f6-44af-b03e-e30408404e5e' : ComponentFunctionalAllocation
                                    allocate function ::> 'eRod_Autonomous_Vehicle_2024 Project'::'eRod_Autonomous_Vehicle_2024'::'Logical Architecture'::'Logical Functions'::'Root Logical Function'.'Control temperature'.'Limit power'
                                    to component ::> 'eRod_Autonomous_Vehicle_2024 Project'::'eRod_Autonomous_Vehicle_2024'::'Logical Architecture'::'Structure'::'eRod System'.'Powertrain'.'ECU'.'Power controll unit';
                                perform 'eRod_Autonomous_Vehicle_2024 Project'::'eRod_Autonomous_Vehicle_2024'::'Logical Architecture'::'Logical Functions'::'Root Logical Function'.'Control temperature'.'Limit power' ; 
                                ref :>> ownedFunctionalAllocation =  ('eRod_Autonomous_Vehicle_2024 Project'::'eRod_Autonomous_Vehicle_2024'::'Logical Architecture'::'Structure'::'eRod System'.'Powertrain'.'ECU'.'Power controll unit'.'e330d57c-24f9-4005-b690-cc06e628421d',
                                'eRod_Autonomous_Vehicle_2024 Project'::'eRod_Autonomous_Vehicle_2024'::'Logical Architecture'::'Structure'::'eRod System'.'Powertrain'.'ECU'.'Power controll unit'.'17e2931c-52f6-44af-b03e-e30408404e5e'); 
                            }  
                            ref :>> ownedLogicalComponents =  ('eRod_Autonomous_Vehicle_2024 Project'::'eRod_Autonomous_Vehicle_2024'::'Logical Architecture'::'Structure'::'eRod System'.'Powertrain'.'ECU'.'Temperature controll unit',
                            'eRod_Autonomous_Vehicle_2024 Project'::'eRod_Autonomous_Vehicle_2024'::'Logical Architecture'::'Structure'::'eRod System'.'Powertrain'.'ECU'.'Power controll unit'); 
                        }  
                        part 'Stator' : LogicalComponent { 
                            @CapellaID { eid = "be936cde-6674-4042-8c14-4dfdd6ffa6fe"; } 
                            attribute :>> isAbstract = false; 
                            attribute :>> isActor = false; 
                            attribute :>> isHuman = false; 
                            allocation '4ff637e7-f816-44bc-a566-8e64ca7730c6' : ComponentFunctionalAllocation
                                allocate function ::> 'eRod_Autonomous_Vehicle_2024 Project'::'eRod_Autonomous_Vehicle_2024'::'Logical Architecture'::'Logical Functions'::'Root Logical Function'.'Provide magnetic field'
                                to component ::> 'eRod_Autonomous_Vehicle_2024 Project'::'eRod_Autonomous_Vehicle_2024'::'Logical Architecture'::'Structure'::'eRod System'.'Powertrain'.'Stator';
                            perform 'eRod_Autonomous_Vehicle_2024 Project'::'eRod_Autonomous_Vehicle_2024'::'Logical Architecture'::'Logical Functions'::'Root Logical Function'.'Provide magnetic field' ; 
                            allocation '920525f5-7112-4190-bb0a-ecf5ef452d9d' : ComponentFunctionalAllocation
                                allocate function ::> 'eRod_Autonomous_Vehicle_2024 Project'::'eRod_Autonomous_Vehicle_2024'::'Logical Architecture'::'Logical Functions'::'Root Logical Function'.'Generate Heat (Stator)'
                                to component ::> 'eRod_Autonomous_Vehicle_2024 Project'::'eRod_Autonomous_Vehicle_2024'::'Logical Architecture'::'Structure'::'eRod System'.'Powertrain'.'Stator';
                            perform 'eRod_Autonomous_Vehicle_2024 Project'::'eRod_Autonomous_Vehicle_2024'::'Logical Architecture'::'Logical Functions'::'Root Logical Function'.'Generate Heat (Stator)' ; 
                            ref :>> ownedFunctionalAllocation =  ('eRod_Autonomous_Vehicle_2024 Project'::'eRod_Autonomous_Vehicle_2024'::'Logical Architecture'::'Structure'::'eRod System'.'Powertrain'.'Stator'.'4ff637e7-f816-44bc-a566-8e64ca7730c6',
                            'eRod_Autonomous_Vehicle_2024 Project'::'eRod_Autonomous_Vehicle_2024'::'Logical Architecture'::'Structure'::'eRod System'.'Powertrain'.'Stator'.'920525f5-7112-4190-bb0a-ecf5ef452d9d'); 
                             
                        }  
                        ref :>> ownedComponentExchanges =  ('eRod_Autonomous_Vehicle_2024 Project'::'eRod_Autonomous_Vehicle_2024'::'Logical Architecture'::'Structure'::'eRod System'.'Powertrain'.'e05e5cb1-7c80-4d09-bad0-728fed629e52',
                        'eRod_Autonomous_Vehicle_2024 Project'::'eRod_Autonomous_Vehicle_2024'::'Logical Architecture'::'Structure'::'eRod System'.'Powertrain'.'c94df1bf-1884-4565-9f7f-bbb958d684f3',
                        'eRod_Autonomous_Vehicle_2024 Project'::'eRod_Autonomous_Vehicle_2024'::'Logical Architecture'::'Structure'::'eRod System'.'Powertrain'.'8a142a49-ae17-4ee6-a80a-5180c9dc9ea6',
                        'eRod_Autonomous_Vehicle_2024 Project'::'eRod_Autonomous_Vehicle_2024'::'Logical Architecture'::'Structure'::'eRod System'.'Powertrain'.'bdcf9155-e91b-46ee-8c79-b9da51929203'); 
                        ref :>> ownedLogicalComponents =  ('eRod_Autonomous_Vehicle_2024 Project'::'eRod_Autonomous_Vehicle_2024'::'Logical Architecture'::'Structure'::'eRod System'.'Powertrain'.'Electric motor',
                        'eRod_Autonomous_Vehicle_2024 Project'::'eRod_Autonomous_Vehicle_2024'::'Logical Architecture'::'Structure'::'eRod System'.'Powertrain'.'Differential',
                        'eRod_Autonomous_Vehicle_2024 Project'::'eRod_Autonomous_Vehicle_2024'::'Logical Architecture'::'Structure'::'eRod System'.'Powertrain'.'Driveshafts',
                        'eRod_Autonomous_Vehicle_2024 Project'::'eRod_Autonomous_Vehicle_2024'::'Logical Architecture'::'Structure'::'eRod System'.'Powertrain'.'Transmission',
                        'eRod_Autonomous_Vehicle_2024 Project'::'eRod_Autonomous_Vehicle_2024'::'Logical Architecture'::'Structure'::'eRod System'.'Powertrain'.'Axies',
                        'eRod_Autonomous_Vehicle_2024 Project'::'eRod_Autonomous_Vehicle_2024'::'Logical Architecture'::'Structure'::'eRod System'.'Powertrain'.'ECU',
                        'eRod_Autonomous_Vehicle_2024 Project'::'eRod_Autonomous_Vehicle_2024'::'Logical Architecture'::'Structure'::'eRod System'.'Powertrain'.'Stator'); 
                    }  
                    part 'Steering System' : LogicalComponent { 
                        @CapellaID { eid = "fd1338b9-b022-4df9-9145-95296678583d"; } 
                        attribute :>> isAbstract = false; 
                        attribute :>> isActor = false; 
                        attribute :>> isHuman = false; 
                        allocation '3c51dbe3-e962-465e-b6c5-d0f3d3679aa5' : ComponentFunctionalAllocation
                            allocate function ::> 'eRod_Autonomous_Vehicle_2024 Project'::'eRod_Autonomous_Vehicle_2024'::'Logical Architecture'::'Logical Functions'::'Root Logical Function'.'Steer Wheels'
                            to component ::> 'eRod_Autonomous_Vehicle_2024 Project'::'eRod_Autonomous_Vehicle_2024'::'Logical Architecture'::'Structure'::'eRod System'.'Steering System';
                        perform 'eRod_Autonomous_Vehicle_2024 Project'::'eRod_Autonomous_Vehicle_2024'::'Logical Architecture'::'Logical Functions'::'Root Logical Function'.'Steer Wheels' ; 
                        ref :>> ownedFunctionalAllocation =  ('eRod_Autonomous_Vehicle_2024 Project'::'eRod_Autonomous_Vehicle_2024'::'Logical Architecture'::'Structure'::'eRod System'.'Steering System'.'3c51dbe3-e962-465e-b6c5-d0f3d3679aa5'); 
                    }  
                    part 'Brake System' : LogicalComponent { 
                        @CapellaID { eid = "6a46436f-a277-4b33-a1c6-8d19f8894eb9"; } 
                        attribute :>> isAbstract = false; 
                        attribute :>> isActor = false; 
                        attribute :>> isHuman = false; 
                        allocation '664af7aa-dd84-4608-b376-c927503c3627' : ComponentFunctionalAllocation
                            allocate function ::> 'eRod_Autonomous_Vehicle_2024 Project'::'eRod_Autonomous_Vehicle_2024'::'Logical Architecture'::'Logical Functions'::'Root Logical Function'.'Slow down and stop the vehicle'
                            to component ::> 'eRod_Autonomous_Vehicle_2024 Project'::'eRod_Autonomous_Vehicle_2024'::'Logical Architecture'::'Structure'::'eRod System'.'Brake System';
                        perform 'eRod_Autonomous_Vehicle_2024 Project'::'eRod_Autonomous_Vehicle_2024'::'Logical Architecture'::'Logical Functions'::'Root Logical Function'.'Slow down and stop the vehicle' ; 
                        allocation '296d348e-d2d5-4b71-9d53-ecd703c07289' : ComponentFunctionalAllocation
                            allocate function ::> 'eRod_Autonomous_Vehicle_2024 Project'::'eRod_Autonomous_Vehicle_2024'::'Logical Architecture'::'Logical Functions'::'Root Logical Function'.'Hold vehicle in place'
                            to component ::> 'eRod_Autonomous_Vehicle_2024 Project'::'eRod_Autonomous_Vehicle_2024'::'Logical Architecture'::'Structure'::'eRod System'.'Brake System';
                        perform 'eRod_Autonomous_Vehicle_2024 Project'::'eRod_Autonomous_Vehicle_2024'::'Logical Architecture'::'Logical Functions'::'Root Logical Function'.'Hold vehicle in place' ; 
                        allocation '2ef7cd42-1636-494a-8512-79bc37152f41' : ComponentFunctionalAllocation
                            allocate function ::> 'eRod_Autonomous_Vehicle_2024 Project'::'eRod_Autonomous_Vehicle_2024'::'Logical Architecture'::'Logical Functions'::'Root Logical Function'.'Measure vehicle speed'
                            to component ::> 'eRod_Autonomous_Vehicle_2024 Project'::'eRod_Autonomous_Vehicle_2024'::'Logical Architecture'::'Structure'::'eRod System'.'Brake System';
                        perform 'eRod_Autonomous_Vehicle_2024 Project'::'eRod_Autonomous_Vehicle_2024'::'Logical Architecture'::'Logical Functions'::'Root Logical Function'.'Measure vehicle speed' ; 
                        interface '6c80a983-5089-40bd-9887-142cf7c33018' : ComponentExchange 
                            connect source ::> 'eRod_Autonomous_Vehicle_2024 Project'::'eRod_Autonomous_Vehicle_2024'::'Logical Architecture'::'Structure'::'eRod System'.'Brake System'.'Brake cylinder'.'CP 1'
                            to  target ::> 'eRod_Autonomous_Vehicle_2024 Project'::'eRod_Autonomous_Vehicle_2024'::'Logical Architecture'::'Structure'::'eRod System'.'Brake System'.'Brake pads'.'CP 1' { 
                            @CapellaID { eid = "6c80a983-5089-40bd-9887-142cf7c33018"; } 
                            attribute :>> kind = ComponentExchangeKind::FLOW; 
                            attribute :>> interfaceName = "C 1"; 
                            attribute :>> isOriented = false; 
                        }  
                        part 'Brake pedal' : LogicalComponent { 
                            @CapellaID { eid = "0b91855a-4cd9-4017-b9cb-cc58f8d8bcab"; } 
                            attribute :>> isAbstract = false; 
                            attribute :>> isActor = false; 
                            attribute :>> isHuman = false; 
                            allocation '0a1450f7-6aaf-4184-a6c2-f9a55e6ef27c' : ComponentFunctionalAllocation
                                allocate function ::> 'eRod_Autonomous_Vehicle_2024 Project'::'eRod_Autonomous_Vehicle_2024'::'Logical Architecture'::'Logical Functions'::'Root Logical Function'.'Slow down and stop the vehicle'.'Brake'
                                to component ::> 'eRod_Autonomous_Vehicle_2024 Project'::'eRod_Autonomous_Vehicle_2024'::'Logical Architecture'::'Structure'::'eRod System'.'Brake System'.'Brake pedal';
                            perform 'eRod_Autonomous_Vehicle_2024 Project'::'eRod_Autonomous_Vehicle_2024'::'Logical Architecture'::'Logical Functions'::'Root Logical Function'.'Slow down and stop the vehicle'.'Brake' ; 
                            ref :>> ownedFunctionalAllocation =  ('eRod_Autonomous_Vehicle_2024 Project'::'eRod_Autonomous_Vehicle_2024'::'Logical Architecture'::'Structure'::'eRod System'.'Brake System'.'Brake pedal'.'0a1450f7-6aaf-4184-a6c2-f9a55e6ef27c'); 
                        }  
                        part 'Brake pads' : LogicalComponent { 
                            @CapellaID { eid = "03e76fc7-c417-4da6-85ab-d1b2276d5666"; } 
                            attribute :>> isAbstract = false; 
                            attribute :>> isActor = false; 
                            attribute :>> isHuman = false; 
                            port 'CP 1' : ComponentPort { 
                                @CapellaID { eid = "ad2d8026-7692-47c4-ac63-5017e668e62a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                            }  
                        }  
                        part 'Brake force sensor' : LogicalComponent { 
                            @CapellaID { eid = "3a9699f0-9a76-40e0-9298-e737f38eaf62"; } 
                            attribute :>> isAbstract = false; 
                            attribute :>> isActor = false; 
                            attribute :>> isHuman = false; 
                            allocation '34ed1f5c-2e1c-429a-adae-77e5375f99ea' : ComponentFunctionalAllocation
                                allocate function ::> 'eRod_Autonomous_Vehicle_2024 Project'::'eRod_Autonomous_Vehicle_2024'::'Logical Architecture'::'Logical Functions'::'Root Logical Function'.'Slow down and stop the vehicle'.'Measure brake force'
                                to component ::> 'eRod_Autonomous_Vehicle_2024 Project'::'eRod_Autonomous_Vehicle_2024'::'Logical Architecture'::'Structure'::'eRod System'.'Brake System'.'Brake force sensor';
                            perform 'eRod_Autonomous_Vehicle_2024 Project'::'eRod_Autonomous_Vehicle_2024'::'Logical Architecture'::'Logical Functions'::'Root Logical Function'.'Slow down and stop the vehicle'.'Measure brake force' ; 
                            ref :>> ownedFunctionalAllocation =  ('eRod_Autonomous_Vehicle_2024 Project'::'eRod_Autonomous_Vehicle_2024'::'Logical Architecture'::'Structure'::'eRod System'.'Brake System'.'Brake force sensor'.'34ed1f5c-2e1c-429a-adae-77e5375f99ea'); 
                        }  
                        part 'Brake cylinder' : LogicalComponent { 
                            @CapellaID { eid = "a14015d2-eab4-488e-a7c0-da8b1d21edaa"; } 
                            attribute :>> isAbstract = false; 
                            attribute :>> isActor = false; 
                            attribute :>> isHuman = false; 
                            allocation 'a724cc00-47ad-4501-a40d-3e3c7d0854d0' : ComponentFunctionalAllocation
                                allocate function ::> 'eRod_Autonomous_Vehicle_2024 Project'::'eRod_Autonomous_Vehicle_2024'::'Logical Architecture'::'Logical Functions'::'Root Logical Function'.'Slow down and stop the vehicle'.'Apply brakes'
                                to component ::> 'eRod_Autonomous_Vehicle_2024 Project'::'eRod_Autonomous_Vehicle_2024'::'Logical Architecture'::'Structure'::'eRod System'.'Brake System'.'Brake cylinder';
                            perform 'eRod_Autonomous_Vehicle_2024 Project'::'eRod_Autonomous_Vehicle_2024'::'Logical Architecture'::'Logical Functions'::'Root Logical Function'.'Slow down and stop the vehicle'.'Apply brakes' ; 
                            allocation 'bbbeff97-c3ab-4804-a166-0f1fbe07c92b' : ComponentFunctionalAllocation
                                allocate function ::> 'eRod_Autonomous_Vehicle_2024 Project'::'eRod_Autonomous_Vehicle_2024'::'Logical Architecture'::'Logical Functions'::'Root Logical Function'.'Slow down and stop the vehicle'.'Release brakes'
                                to component ::> 'eRod_Autonomous_Vehicle_2024 Project'::'eRod_Autonomous_Vehicle_2024'::'Logical Architecture'::'Structure'::'eRod System'.'Brake System'.'Brake cylinder';
                            perform 'eRod_Autonomous_Vehicle_2024 Project'::'eRod_Autonomous_Vehicle_2024'::'Logical Architecture'::'Logical Functions'::'Root Logical Function'.'Slow down and stop the vehicle'.'Release brakes' ; 
                            port 'CP 1' : ComponentPort { 
                                @CapellaID { eid = "092673b7-ec04-4228-8518-b7052302303f"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                            }  
                            ref :>> ownedFunctionalAllocation =  ('eRod_Autonomous_Vehicle_2024 Project'::'eRod_Autonomous_Vehicle_2024'::'Logical Architecture'::'Structure'::'eRod System'.'Brake System'.'Brake cylinder'.'a724cc00-47ad-4501-a40d-3e3c7d0854d0',
                            'eRod_Autonomous_Vehicle_2024 Project'::'eRod_Autonomous_Vehicle_2024'::'Logical Architecture'::'Structure'::'eRod System'.'Brake System'.'Brake cylinder'.'bbbeff97-c3ab-4804-a166-0f1fbe07c92b'); 
                        }  
                        part 'Wheel speed sensor' : LogicalComponent { 
                            @CapellaID { eid = "3837804b-213c-42ac-8041-f03179d8b0fc"; } 
                            attribute :>> isAbstract = false; 
                            attribute :>> isActor = false; 
                            attribute :>> isHuman = false; 
                            allocation 'b2f9cc76-b812-405e-8912-0e203c8402d7' : ComponentFunctionalAllocation
                                allocate function ::> 'eRod_Autonomous_Vehicle_2024 Project'::'eRod_Autonomous_Vehicle_2024'::'Logical Architecture'::'Logical Functions'::'Root Logical Function'.'Slow down and stop the vehicle'.'Measure wheel rotation speed'
                                to component ::> 'eRod_Autonomous_Vehicle_2024 Project'::'eRod_Autonomous_Vehicle_2024'::'Logical Architecture'::'Structure'::'eRod System'.'Brake System'.'Wheel speed sensor';
                            perform 'eRod_Autonomous_Vehicle_2024 Project'::'eRod_Autonomous_Vehicle_2024'::'Logical Architecture'::'Logical Functions'::'Root Logical Function'.'Slow down and stop the vehicle'.'Measure wheel rotation speed' ; 
                            ref :>> ownedFunctionalAllocation =  ('eRod_Autonomous_Vehicle_2024 Project'::'eRod_Autonomous_Vehicle_2024'::'Logical Architecture'::'Structure'::'eRod System'.'Brake System'.'Wheel speed sensor'.'b2f9cc76-b812-405e-8912-0e203c8402d7'); 
                        }  
                        part 'ABS Controller' : LogicalComponent { 
                            @CapellaID { eid = "a2bc9a2d-33c5-4c24-95ca-db274a412011"; } 
                            attribute :>> isAbstract = false; 
                            attribute :>> isActor = false; 
                            attribute :>> isHuman = false; 
                            allocation '7d79f5d1-6f04-4ac7-89a4-25cdacfe2fcb' : ComponentFunctionalAllocation
                                allocate function ::> 'eRod_Autonomous_Vehicle_2024 Project'::'eRod_Autonomous_Vehicle_2024'::'Logical Architecture'::'Logical Functions'::'Root Logical Function'.'Slow down and stop the vehicle'.'Detect locked wheels'
                                to component ::> 'eRod_Autonomous_Vehicle_2024 Project'::'eRod_Autonomous_Vehicle_2024'::'Logical Architecture'::'Structure'::'eRod System'.'Brake System'.'ABS Controller';
                            perform 'eRod_Autonomous_Vehicle_2024 Project'::'eRod_Autonomous_Vehicle_2024'::'Logical Architecture'::'Logical Functions'::'Root Logical Function'.'Slow down and stop the vehicle'.'Detect locked wheels' ; 
                            ref :>> ownedFunctionalAllocation =  ('eRod_Autonomous_Vehicle_2024 Project'::'eRod_Autonomous_Vehicle_2024'::'Logical Architecture'::'Structure'::'eRod System'.'Brake System'.'ABS Controller'.'7d79f5d1-6f04-4ac7-89a4-25cdacfe2fcb'); 
                        }  
                        ref :>> ownedFunctionalAllocation =  ('eRod_Autonomous_Vehicle_2024 Project'::'eRod_Autonomous_Vehicle_2024'::'Logical Architecture'::'Structure'::'eRod System'.'Brake System'.'664af7aa-dd84-4608-b376-c927503c3627',
                        'eRod_Autonomous_Vehicle_2024 Project'::'eRod_Autonomous_Vehicle_2024'::'Logical Architecture'::'Structure'::'eRod System'.'Brake System'.'296d348e-d2d5-4b71-9d53-ecd703c07289',
                        'eRod_Autonomous_Vehicle_2024 Project'::'eRod_Autonomous_Vehicle_2024'::'Logical Architecture'::'Structure'::'eRod System'.'Brake System'.'2ef7cd42-1636-494a-8512-79bc37152f41'); 
                        ref :>> ownedComponentExchanges =  ('eRod_Autonomous_Vehicle_2024 Project'::'eRod_Autonomous_Vehicle_2024'::'Logical Architecture'::'Structure'::'eRod System'.'Brake System'.'6c80a983-5089-40bd-9887-142cf7c33018'); 
                        ref :>> ownedLogicalComponents =  ('eRod_Autonomous_Vehicle_2024 Project'::'eRod_Autonomous_Vehicle_2024'::'Logical Architecture'::'Structure'::'eRod System'.'Brake System'.'Brake pedal',
                        'eRod_Autonomous_Vehicle_2024 Project'::'eRod_Autonomous_Vehicle_2024'::'Logical Architecture'::'Structure'::'eRod System'.'Brake System'.'Brake pads',
                        'eRod_Autonomous_Vehicle_2024 Project'::'eRod_Autonomous_Vehicle_2024'::'Logical Architecture'::'Structure'::'eRod System'.'Brake System'.'Brake force sensor',
                        'eRod_Autonomous_Vehicle_2024 Project'::'eRod_Autonomous_Vehicle_2024'::'Logical Architecture'::'Structure'::'eRod System'.'Brake System'.'Brake cylinder',
                        'eRod_Autonomous_Vehicle_2024 Project'::'eRod_Autonomous_Vehicle_2024'::'Logical Architecture'::'Structure'::'eRod System'.'Brake System'.'Wheel speed sensor',
                        'eRod_Autonomous_Vehicle_2024 Project'::'eRod_Autonomous_Vehicle_2024'::'Logical Architecture'::'Structure'::'eRod System'.'Brake System'.'ABS Controller'); 
                    }  
                    part 'Battery System' : LogicalComponent { 
                        @CapellaID { eid = "bc7c8bd8-32f2-4746-a447-c506d36a7b2f"; } 
                        attribute :>> isAbstract = false; 
                        attribute :>> isActor = false; 
                        attribute :>> isHuman = false; 
                        part 'Battery' : LogicalComponent { 
                            @CapellaID { eid = "4d817055-0dfd-4c81-ae77-1f44de085b53"; } 
                            attribute :>> isAbstract = false; 
                            attribute :>> isActor = false; 
                            attribute :>> isHuman = false; 
                            allocation '1b094190-7cc1-412c-b332-7f56237b3b1e' : ComponentFunctionalAllocation
                                allocate function ::> 'eRod_Autonomous_Vehicle_2024 Project'::'eRod_Autonomous_Vehicle_2024'::'Logical Architecture'::'Logical Functions'::'Root Logical Function'.'Provide electrical energy'
                                to component ::> 'eRod_Autonomous_Vehicle_2024 Project'::'eRod_Autonomous_Vehicle_2024'::'Logical Architecture'::'Structure'::'eRod System'.'Battery System'.'Battery';
                            perform 'eRod_Autonomous_Vehicle_2024 Project'::'eRod_Autonomous_Vehicle_2024'::'Logical Architecture'::'Logical Functions'::'Root Logical Function'.'Provide electrical energy' ; 
                            allocation '3368039c-51c6-428f-86c3-7b7a1bcd7f55' : ComponentFunctionalAllocation
                                allocate function ::> 'eRod_Autonomous_Vehicle_2024 Project'::'eRod_Autonomous_Vehicle_2024'::'Logical Architecture'::'Logical Functions'::'Root Logical Function'.'Store energy'
                                to component ::> 'eRod_Autonomous_Vehicle_2024 Project'::'eRod_Autonomous_Vehicle_2024'::'Logical Architecture'::'Structure'::'eRod System'.'Battery System'.'Battery';
                            perform 'eRod_Autonomous_Vehicle_2024 Project'::'eRod_Autonomous_Vehicle_2024'::'Logical Architecture'::'Logical Functions'::'Root Logical Function'.'Store energy' ; 
                            port 'CP 1' : ComponentPort { 
                                @CapellaID { eid = "c7ccc0f1-e22e-43f2-a371-e2f6fa2c5e95"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                            }  
                            port 'Battery to Motor' : ComponentPort { 
                                @CapellaID { eid = "c926fa03-6da1-43c7-aef9-984bce9eee80"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                                ref :>> providedInterfaces =  ('eRod_Autonomous_Vehicle_2024 Project'::'eRod_Autonomous_Vehicle_2024'::'Logical Architecture'::'Interfaces'::'Electricity'); 
                            }  
                            ref :>> ownedFunctionalAllocation =  ('eRod_Autonomous_Vehicle_2024 Project'::'eRod_Autonomous_Vehicle_2024'::'Logical Architecture'::'Structure'::'eRod System'.'Battery System'.'Battery'.'1b094190-7cc1-412c-b332-7f56237b3b1e',
                            'eRod_Autonomous_Vehicle_2024 Project'::'eRod_Autonomous_Vehicle_2024'::'Logical Architecture'::'Structure'::'eRod System'.'Battery System'.'Battery'.'3368039c-51c6-428f-86c3-7b7a1bcd7f55'); 
                             
                        }  
                        ref :>> ownedLogicalComponents =  ('eRod_Autonomous_Vehicle_2024 Project'::'eRod_Autonomous_Vehicle_2024'::'Logical Architecture'::'Structure'::'eRod System'.'Battery System'.'Battery'); 
                    }  
                    part 'Lights' : LogicalComponent { 
                        @CapellaID { eid = "42cb8178-d914-432d-9cf0-63913f1a4346"; } 
                        attribute :>> isAbstract = false; 
                        attribute :>> isActor = false; 
                        attribute :>> isHuman = false; 
                        allocation 'ad8a370d-1b6c-427d-8b72-0e572454f053' : ComponentFunctionalAllocation
                            allocate function ::> 'eRod_Autonomous_Vehicle_2024 Project'::'eRod_Autonomous_Vehicle_2024'::'Logical Architecture'::'Logical Functions'::'Root Logical Function'.'Light up the road'
                            to component ::> 'eRod_Autonomous_Vehicle_2024 Project'::'eRod_Autonomous_Vehicle_2024'::'Logical Architecture'::'Structure'::'eRod System'.'Lights';
                        perform 'eRod_Autonomous_Vehicle_2024 Project'::'eRod_Autonomous_Vehicle_2024'::'Logical Architecture'::'Logical Functions'::'Root Logical Function'.'Light up the road' ; 
                        allocation '8fa5207a-1f5d-4e07-9eba-21d23dc4d16c' : ComponentFunctionalAllocation
                            allocate function ::> 'eRod_Autonomous_Vehicle_2024 Project'::'eRod_Autonomous_Vehicle_2024'::'Logical Architecture'::'Logical Functions'::'Root Logical Function'.'Warn and show intent to other trafficants'
                            to component ::> 'eRod_Autonomous_Vehicle_2024 Project'::'eRod_Autonomous_Vehicle_2024'::'Logical Architecture'::'Structure'::'eRod System'.'Lights';
                        perform 'eRod_Autonomous_Vehicle_2024 Project'::'eRod_Autonomous_Vehicle_2024'::'Logical Architecture'::'Logical Functions'::'Root Logical Function'.'Warn and show intent to other trafficants' ; 
                        part 'Brake lights' : LogicalComponent { 
                            @CapellaID { eid = "a96dcb49-5055-467f-a1b7-4621fcb87533"; } 
                            attribute :>> isAbstract = false; 
                            attribute :>> isActor = false; 
                            attribute :>> isHuman = false; 
                            allocation '59bad2b6-e9da-4487-9761-12667793ae05' : ComponentFunctionalAllocation
                                allocate function ::> 'eRod_Autonomous_Vehicle_2024 Project'::'eRod_Autonomous_Vehicle_2024'::'Logical Architecture'::'Logical Functions'::'Root Logical Function'.'Warn and show intent to other trafficants'.'Turn on brake lights'
                                to component ::> 'eRod_Autonomous_Vehicle_2024 Project'::'eRod_Autonomous_Vehicle_2024'::'Logical Architecture'::'Structure'::'eRod System'.'Lights'.'Brake lights';
                            perform 'eRod_Autonomous_Vehicle_2024 Project'::'eRod_Autonomous_Vehicle_2024'::'Logical Architecture'::'Logical Functions'::'Root Logical Function'.'Warn and show intent to other trafficants'.'Turn on brake lights' ; 
                            ref :>> ownedFunctionalAllocation =  ('eRod_Autonomous_Vehicle_2024 Project'::'eRod_Autonomous_Vehicle_2024'::'Logical Architecture'::'Structure'::'eRod System'.'Lights'.'Brake lights'.'59bad2b6-e9da-4487-9761-12667793ae05'); 
                        }  
                        ref :>> ownedFunctionalAllocation =  ('eRod_Autonomous_Vehicle_2024 Project'::'eRod_Autonomous_Vehicle_2024'::'Logical Architecture'::'Structure'::'eRod System'.'Lights'.'ad8a370d-1b6c-427d-8b72-0e572454f053',
                        'eRod_Autonomous_Vehicle_2024 Project'::'eRod_Autonomous_Vehicle_2024'::'Logical Architecture'::'Structure'::'eRod System'.'Lights'.'8fa5207a-1f5d-4e07-9eba-21d23dc4d16c'); 
                        ref :>> ownedLogicalComponents =  ('eRod_Autonomous_Vehicle_2024 Project'::'eRod_Autonomous_Vehicle_2024'::'Logical Architecture'::'Structure'::'eRod System'.'Lights'.'Brake lights'); 
                    }  
                    part 'Autonomous Vehicle (AV) System' : LogicalComponent { 
                        @CapellaID { eid = "a4deac82-0165-4df0-b362-ee1370683fc7"; } 
                        attribute :>> isAbstract = false; 
                        attribute :>> isActor = false; 
                        attribute :>> isHuman = false; 
                        allocation 'f6756e54-863a-403d-b1c2-715cd1d350f7' : ComponentFunctionalAllocation
                            allocate function ::> 'eRod_Autonomous_Vehicle_2024 Project'::'eRod_Autonomous_Vehicle_2024'::'Logical Architecture'::'Logical Functions'::'Root Logical Function'.'Park vehicle'
                            to component ::> 'eRod_Autonomous_Vehicle_2024 Project'::'eRod_Autonomous_Vehicle_2024'::'Logical Architecture'::'Structure'::'eRod System'.'Autonomous Vehicle (AV) System';
                        perform 'eRod_Autonomous_Vehicle_2024 Project'::'eRod_Autonomous_Vehicle_2024'::'Logical Architecture'::'Logical Functions'::'Root Logical Function'.'Park vehicle' ; 
                        part 'Perception' : LogicalComponent { 
                            @CapellaID { eid = "097da369-63b6-4970-a14d-53c670ba8d5f"; } 
                            attribute :>> isAbstract = false; 
                            attribute :>> isActor = false; 
                            attribute :>> isHuman = false; 
                            allocation '6c617a2b-3105-475b-b542-93bd0f67788e' : ComponentFunctionalAllocation
                                allocate function ::> 'eRod_Autonomous_Vehicle_2024 Project'::'eRod_Autonomous_Vehicle_2024'::'Logical Architecture'::'Logical Functions'::'Root Logical Function'.'Detect obstacles'
                                to component ::> 'eRod_Autonomous_Vehicle_2024 Project'::'eRod_Autonomous_Vehicle_2024'::'Logical Architecture'::'Structure'::'eRod System'.'Autonomous Vehicle (AV) System'.'Perception';
                            perform 'eRod_Autonomous_Vehicle_2024 Project'::'eRod_Autonomous_Vehicle_2024'::'Logical Architecture'::'Logical Functions'::'Root Logical Function'.'Detect obstacles' ; 
                            allocation '5ef9a375-2f46-4899-a0f1-83c14b19bee0' : ComponentFunctionalAllocation
                                allocate function ::> 'eRod_Autonomous_Vehicle_2024 Project'::'eRod_Autonomous_Vehicle_2024'::'Logical Architecture'::'Logical Functions'::'Root Logical Function'.'Detect road'.'Detect path'
                                to component ::> 'eRod_Autonomous_Vehicle_2024 Project'::'eRod_Autonomous_Vehicle_2024'::'Logical Architecture'::'Structure'::'eRod System'.'Autonomous Vehicle (AV) System'.'Perception';
                            perform 'eRod_Autonomous_Vehicle_2024 Project'::'eRod_Autonomous_Vehicle_2024'::'Logical Architecture'::'Logical Functions'::'Root Logical Function'.'Detect road'.'Detect path' ; 
                            allocation '9d580f49-380b-4c64-b725-40ba2c4c42eb' : ComponentFunctionalAllocation
                                allocate function ::> 'eRod_Autonomous_Vehicle_2024 Project'::'eRod_Autonomous_Vehicle_2024'::'Logical Architecture'::'Logical Functions'::'Root Logical Function'.'Detect intersections'
                                to component ::> 'eRod_Autonomous_Vehicle_2024 Project'::'eRod_Autonomous_Vehicle_2024'::'Logical Architecture'::'Structure'::'eRod System'.'Autonomous Vehicle (AV) System'.'Perception';
                            perform 'eRod_Autonomous_Vehicle_2024 Project'::'eRod_Autonomous_Vehicle_2024'::'Logical Architecture'::'Logical Functions'::'Root Logical Function'.'Detect intersections' ; 
                            allocation 'f21aea5e-035a-42c2-b772-3f05f39533b3' : ComponentFunctionalAllocation
                                allocate function ::> 'eRod_Autonomous_Vehicle_2024 Project'::'eRod_Autonomous_Vehicle_2024'::'Logical Architecture'::'Logical Functions'::'Root Logical Function'.'Detect signs'
                                to component ::> 'eRod_Autonomous_Vehicle_2024 Project'::'eRod_Autonomous_Vehicle_2024'::'Logical Architecture'::'Structure'::'eRod System'.'Autonomous Vehicle (AV) System'.'Perception';
                            perform 'eRod_Autonomous_Vehicle_2024 Project'::'eRod_Autonomous_Vehicle_2024'::'Logical Architecture'::'Logical Functions'::'Root Logical Function'.'Detect signs' ; 
                            allocation '5979b439-694e-4168-911e-b532953fdfb4' : ComponentFunctionalAllocation
                                allocate function ::> 'eRod_Autonomous_Vehicle_2024 Project'::'eRod_Autonomous_Vehicle_2024'::'Logical Architecture'::'Logical Functions'::'Root Logical Function'.'Detect lights'
                                to component ::> 'eRod_Autonomous_Vehicle_2024 Project'::'eRod_Autonomous_Vehicle_2024'::'Logical Architecture'::'Structure'::'eRod System'.'Autonomous Vehicle (AV) System'.'Perception';
                            perform 'eRod_Autonomous_Vehicle_2024 Project'::'eRod_Autonomous_Vehicle_2024'::'Logical Architecture'::'Logical Functions'::'Root Logical Function'.'Detect lights' ; 
                            allocation '03392835-d26a-4961-9678-0df4d7f12cc2' : ComponentFunctionalAllocation
                                allocate function ::> 'eRod_Autonomous_Vehicle_2024 Project'::'eRod_Autonomous_Vehicle_2024'::'Logical Architecture'::'Logical Functions'::'Root Logical Function'.'Detect road'.'Image fusion'
                                to component ::> 'eRod_Autonomous_Vehicle_2024 Project'::'eRod_Autonomous_Vehicle_2024'::'Logical Architecture'::'Structure'::'eRod System'.'Autonomous Vehicle (AV) System'.'Perception';
                            perform 'eRod_Autonomous_Vehicle_2024 Project'::'eRod_Autonomous_Vehicle_2024'::'Logical Architecture'::'Logical Functions'::'Root Logical Function'.'Detect road'.'Image fusion' ; 
                            ref :>> ownedFunctionalAllocation =  ('eRod_Autonomous_Vehicle_2024 Project'::'eRod_Autonomous_Vehicle_2024'::'Logical Architecture'::'Structure'::'eRod System'.'Autonomous Vehicle (AV) System'.'Perception'.'6c617a2b-3105-475b-b542-93bd0f67788e',
                            'eRod_Autonomous_Vehicle_2024 Project'::'eRod_Autonomous_Vehicle_2024'::'Logical Architecture'::'Structure'::'eRod System'.'Autonomous Vehicle (AV) System'.'Perception'.'5ef9a375-2f46-4899-a0f1-83c14b19bee0',
                            'eRod_Autonomous_Vehicle_2024 Project'::'eRod_Autonomous_Vehicle_2024'::'Logical Architecture'::'Structure'::'eRod System'.'Autonomous Vehicle (AV) System'.'Perception'.'9d580f49-380b-4c64-b725-40ba2c4c42eb',
                            'eRod_Autonomous_Vehicle_2024 Project'::'eRod_Autonomous_Vehicle_2024'::'Logical Architecture'::'Structure'::'eRod System'.'Autonomous Vehicle (AV) System'.'Perception'.'f21aea5e-035a-42c2-b772-3f05f39533b3',
                            'eRod_Autonomous_Vehicle_2024 Project'::'eRod_Autonomous_Vehicle_2024'::'Logical Architecture'::'Structure'::'eRod System'.'Autonomous Vehicle (AV) System'.'Perception'.'5979b439-694e-4168-911e-b532953fdfb4',
                            'eRod_Autonomous_Vehicle_2024 Project'::'eRod_Autonomous_Vehicle_2024'::'Logical Architecture'::'Structure'::'eRod System'.'Autonomous Vehicle (AV) System'.'Perception'.'03392835-d26a-4961-9678-0df4d7f12cc2'); 
                        }  
                        part 'Auto Drive' : LogicalComponent { 
                            @CapellaID { eid = "fdbbc39e-abd8-4d27-8fbd-f9349c1d5a0f"; } 
                            attribute :>> isAbstract = false; 
                            attribute :>> isActor = false; 
                            attribute :>> isHuman = false; 
                            allocation '098113ac-4500-4d8d-8652-5f50a7735812' : ComponentFunctionalAllocation
                                allocate function ::> 'eRod_Autonomous_Vehicle_2024 Project'::'eRod_Autonomous_Vehicle_2024'::'Logical Architecture'::'Logical Functions'::'Root Logical Function'.'Drive route'
                                to component ::> 'eRod_Autonomous_Vehicle_2024 Project'::'eRod_Autonomous_Vehicle_2024'::'Logical Architecture'::'Structure'::'eRod System'.'Autonomous Vehicle (AV) System'.'Auto Drive';
                            perform 'eRod_Autonomous_Vehicle_2024 Project'::'eRod_Autonomous_Vehicle_2024'::'Logical Architecture'::'Logical Functions'::'Root Logical Function'.'Drive route' ; 
                            allocation 'afbdc536-82e5-422c-8142-9844332f3da1' : ComponentFunctionalAllocation
                                allocate function ::> 'eRod_Autonomous_Vehicle_2024 Project'::'eRod_Autonomous_Vehicle_2024'::'Logical Architecture'::'Logical Functions'::'Root Logical Function'.'Automatic Steering'
                                to component ::> 'eRod_Autonomous_Vehicle_2024 Project'::'eRod_Autonomous_Vehicle_2024'::'Logical Architecture'::'Structure'::'eRod System'.'Autonomous Vehicle (AV) System'.'Auto Drive';
                            perform 'eRod_Autonomous_Vehicle_2024 Project'::'eRod_Autonomous_Vehicle_2024'::'Logical Architecture'::'Logical Functions'::'Root Logical Function'.'Automatic Steering' ; 
                            allocation '8167f5ce-0b44-4105-b9ae-5705dc618076' : ComponentFunctionalAllocation
                                allocate function ::> 'eRod_Autonomous_Vehicle_2024 Project'::'eRod_Autonomous_Vehicle_2024'::'Logical Architecture'::'Logical Functions'::'Root Logical Function'.'Avoid collision'
                                to component ::> 'eRod_Autonomous_Vehicle_2024 Project'::'eRod_Autonomous_Vehicle_2024'::'Logical Architecture'::'Structure'::'eRod System'.'Autonomous Vehicle (AV) System'.'Auto Drive';
                            perform 'eRod_Autonomous_Vehicle_2024 Project'::'eRod_Autonomous_Vehicle_2024'::'Logical Architecture'::'Logical Functions'::'Root Logical Function'.'Avoid collision' ; 
                            allocation '0a933d92-af32-4b88-85d9-7d5e0312788e' : ComponentFunctionalAllocation
                                allocate function ::> 'eRod_Autonomous_Vehicle_2024 Project'::'eRod_Autonomous_Vehicle_2024'::'Logical Architecture'::'Logical Functions'::'Root Logical Function'.'Status and command indication'
                                to component ::> 'eRod_Autonomous_Vehicle_2024 Project'::'eRod_Autonomous_Vehicle_2024'::'Logical Architecture'::'Structure'::'eRod System'.'Autonomous Vehicle (AV) System'.'Auto Drive';
                            perform 'eRod_Autonomous_Vehicle_2024 Project'::'eRod_Autonomous_Vehicle_2024'::'Logical Architecture'::'Logical Functions'::'Root Logical Function'.'Status and command indication' ; 
                            ref :>> ownedFunctionalAllocation =  ('eRod_Autonomous_Vehicle_2024 Project'::'eRod_Autonomous_Vehicle_2024'::'Logical Architecture'::'Structure'::'eRod System'.'Autonomous Vehicle (AV) System'.'Auto Drive'.'098113ac-4500-4d8d-8652-5f50a7735812',
                            'eRod_Autonomous_Vehicle_2024 Project'::'eRod_Autonomous_Vehicle_2024'::'Logical Architecture'::'Structure'::'eRod System'.'Autonomous Vehicle (AV) System'.'Auto Drive'.'afbdc536-82e5-422c-8142-9844332f3da1',
                            'eRod_Autonomous_Vehicle_2024 Project'::'eRod_Autonomous_Vehicle_2024'::'Logical Architecture'::'Structure'::'eRod System'.'Autonomous Vehicle (AV) System'.'Auto Drive'.'8167f5ce-0b44-4105-b9ae-5705dc618076',
                            'eRod_Autonomous_Vehicle_2024 Project'::'eRod_Autonomous_Vehicle_2024'::'Logical Architecture'::'Structure'::'eRod System'.'Autonomous Vehicle (AV) System'.'Auto Drive'.'0a933d92-af32-4b88-85d9-7d5e0312788e'); 
                        }  
                        part 'Park Assist' : LogicalComponent { 
                            @CapellaID { eid = "66ecf20c-462c-45cc-b453-85ba0d4f26e4"; } 
                            attribute :>> isAbstract = false; 
                            attribute :>> isActor = false; 
                            attribute :>> isHuman = false; 
                            allocation '71264077-6afb-45c9-a7e5-1457cb7878c5' : ComponentFunctionalAllocation
                                allocate function ::> 'eRod_Autonomous_Vehicle_2024 Project'::'eRod_Autonomous_Vehicle_2024'::'Logical Architecture'::'Logical Functions'::'Root Logical Function'.'Calculate Driving Path'
                                to component ::> 'eRod_Autonomous_Vehicle_2024 Project'::'eRod_Autonomous_Vehicle_2024'::'Logical Architecture'::'Structure'::'eRod System'.'Autonomous Vehicle (AV) System'.'Park Assist';
                            perform 'eRod_Autonomous_Vehicle_2024 Project'::'eRod_Autonomous_Vehicle_2024'::'Logical Architecture'::'Logical Functions'::'Root Logical Function'.'Calculate Driving Path' ; 
                            allocation '0659bd20-ea5c-4b55-804c-0282475ca04e' : ComponentFunctionalAllocation
                                allocate function ::> 'eRod_Autonomous_Vehicle_2024 Project'::'eRod_Autonomous_Vehicle_2024'::'Logical Architecture'::'Logical Functions'::'Root Logical Function'.'Display State of Park'
                                to component ::> 'eRod_Autonomous_Vehicle_2024 Project'::'eRod_Autonomous_Vehicle_2024'::'Logical Architecture'::'Structure'::'eRod System'.'Autonomous Vehicle (AV) System'.'Park Assist';
                            perform 'eRod_Autonomous_Vehicle_2024 Project'::'eRod_Autonomous_Vehicle_2024'::'Logical Architecture'::'Logical Functions'::'Root Logical Function'.'Display State of Park' ; 
                            ref :>> ownedFunctionalAllocation =  ('eRod_Autonomous_Vehicle_2024 Project'::'eRod_Autonomous_Vehicle_2024'::'Logical Architecture'::'Structure'::'eRod System'.'Autonomous Vehicle (AV) System'.'Park Assist'.'71264077-6afb-45c9-a7e5-1457cb7878c5',
                            'eRod_Autonomous_Vehicle_2024 Project'::'eRod_Autonomous_Vehicle_2024'::'Logical Architecture'::'Structure'::'eRod System'.'Autonomous Vehicle (AV) System'.'Park Assist'.'0659bd20-ea5c-4b55-804c-0282475ca04e'); 
                        }  
                        part 'Mapping' : LogicalComponent { 
                            @CapellaID { eid = "611363de-edb8-4d95-acb5-c15c3aa3d155"; } 
                            attribute :>> isAbstract = false; 
                            attribute :>> isActor = false; 
                            attribute :>> isHuman = false; 
                            allocation '8bacab9a-85eb-4fcd-8a7c-193d21cf13ca' : ComponentFunctionalAllocation
                                allocate function ::> 'eRod_Autonomous_Vehicle_2024 Project'::'eRod_Autonomous_Vehicle_2024'::'Logical Architecture'::'Logical Functions'::'Root Logical Function'.'Plan path'
                                to component ::> 'eRod_Autonomous_Vehicle_2024 Project'::'eRod_Autonomous_Vehicle_2024'::'Logical Architecture'::'Structure'::'eRod System'.'Autonomous Vehicle (AV) System'.'Mapping';
                            perform 'eRod_Autonomous_Vehicle_2024 Project'::'eRod_Autonomous_Vehicle_2024'::'Logical Architecture'::'Logical Functions'::'Root Logical Function'.'Plan path' ; 
                            allocation '6bccfd52-f8b6-460d-a40a-38ccf091edf8' : ComponentFunctionalAllocation
                                allocate function ::> 'eRod_Autonomous_Vehicle_2024 Project'::'eRod_Autonomous_Vehicle_2024'::'Logical Architecture'::'Logical Functions'::'Root Logical Function'.'Locate targets'
                                to component ::> 'eRod_Autonomous_Vehicle_2024 Project'::'eRod_Autonomous_Vehicle_2024'::'Logical Architecture'::'Structure'::'eRod System'.'Autonomous Vehicle (AV) System'.'Mapping';
                            perform 'eRod_Autonomous_Vehicle_2024 Project'::'eRod_Autonomous_Vehicle_2024'::'Logical Architecture'::'Logical Functions'::'Root Logical Function'.'Locate targets' ; 
                            allocation '69f1dd36-fa38-469b-b135-eb3f4c65159c' : ComponentFunctionalAllocation
                                allocate function ::> 'eRod_Autonomous_Vehicle_2024 Project'::'eRod_Autonomous_Vehicle_2024'::'Logical Architecture'::'Logical Functions'::'Root Logical Function'.'Provide object location'
                                to component ::> 'eRod_Autonomous_Vehicle_2024 Project'::'eRod_Autonomous_Vehicle_2024'::'Logical Architecture'::'Structure'::'eRod System'.'Autonomous Vehicle (AV) System'.'Mapping';
                            perform 'eRod_Autonomous_Vehicle_2024 Project'::'eRod_Autonomous_Vehicle_2024'::'Logical Architecture'::'Logical Functions'::'Root Logical Function'.'Provide object location' ; 
                            allocation '29d7014b-1192-4d70-b7ce-956572986fe0' : ComponentFunctionalAllocation
                                allocate function ::> 'eRod_Autonomous_Vehicle_2024 Project'::'eRod_Autonomous_Vehicle_2024'::'Logical Architecture'::'Logical Functions'::'Root Logical Function'.'Provide parking location'
                                to component ::> 'eRod_Autonomous_Vehicle_2024 Project'::'eRod_Autonomous_Vehicle_2024'::'Logical Architecture'::'Structure'::'eRod System'.'Autonomous Vehicle (AV) System'.'Mapping';
                            perform 'eRod_Autonomous_Vehicle_2024 Project'::'eRod_Autonomous_Vehicle_2024'::'Logical Architecture'::'Logical Functions'::'Root Logical Function'.'Provide parking location' ; 
                            ref :>> ownedFunctionalAllocation =  ('eRod_Autonomous_Vehicle_2024 Project'::'eRod_Autonomous_Vehicle_2024'::'Logical Architecture'::'Structure'::'eRod System'.'Autonomous Vehicle (AV) System'.'Mapping'.'8bacab9a-85eb-4fcd-8a7c-193d21cf13ca',
                            'eRod_Autonomous_Vehicle_2024 Project'::'eRod_Autonomous_Vehicle_2024'::'Logical Architecture'::'Structure'::'eRod System'.'Autonomous Vehicle (AV) System'.'Mapping'.'6bccfd52-f8b6-460d-a40a-38ccf091edf8',
                            'eRod_Autonomous_Vehicle_2024 Project'::'eRod_Autonomous_Vehicle_2024'::'Logical Architecture'::'Structure'::'eRod System'.'Autonomous Vehicle (AV) System'.'Mapping'.'69f1dd36-fa38-469b-b135-eb3f4c65159c',
                            'eRod_Autonomous_Vehicle_2024 Project'::'eRod_Autonomous_Vehicle_2024'::'Logical Architecture'::'Structure'::'eRod System'.'Autonomous Vehicle (AV) System'.'Mapping'.'29d7014b-1192-4d70-b7ce-956572986fe0'); 
                        }  
                        part 'Accell Control' : LogicalComponent { 
                            @CapellaID { eid = "0a0e0a49-12da-450b-a782-8e7b4ed4ac98"; } 
                            attribute :>> isAbstract = false; 
                            attribute :>> isActor = false; 
                            attribute :>> isHuman = false; 
                            allocation '02d4f1e0-9207-4a51-80d1-61c0e050def1' : ComponentFunctionalAllocation
                                allocate function ::> 'eRod_Autonomous_Vehicle_2024 Project'::'eRod_Autonomous_Vehicle_2024'::'Logical Architecture'::'Logical Functions'::'Root Logical Function'.'Control Accel'
                                to component ::> 'eRod_Autonomous_Vehicle_2024 Project'::'eRod_Autonomous_Vehicle_2024'::'Logical Architecture'::'Structure'::'eRod System'.'Autonomous Vehicle (AV) System'.'Accell Control';
                            perform 'eRod_Autonomous_Vehicle_2024 Project'::'eRod_Autonomous_Vehicle_2024'::'Logical Architecture'::'Logical Functions'::'Root Logical Function'.'Control Accel' ; 
                            ref :>> ownedFunctionalAllocation =  ('eRod_Autonomous_Vehicle_2024 Project'::'eRod_Autonomous_Vehicle_2024'::'Logical Architecture'::'Structure'::'eRod System'.'Autonomous Vehicle (AV) System'.'Accell Control'.'02d4f1e0-9207-4a51-80d1-61c0e050def1'); 
                        }  
                        part 'Steering Control' : LogicalComponent { 
                            @CapellaID { eid = "9a6b94b5-3955-4fe7-990d-2c52ec92997a"; } 
                            attribute :>> isAbstract = false; 
                            attribute :>> isActor = false; 
                            attribute :>> isHuman = false; 
                            allocation '5b1fcd96-e5d3-4fc4-a2f1-aa0d6247a36b' : ComponentFunctionalAllocation
                                allocate function ::> 'eRod_Autonomous_Vehicle_2024 Project'::'eRod_Autonomous_Vehicle_2024'::'Logical Architecture'::'Logical Functions'::'Root Logical Function'.'Automatic Steer'
                                to component ::> 'eRod_Autonomous_Vehicle_2024 Project'::'eRod_Autonomous_Vehicle_2024'::'Logical Architecture'::'Structure'::'eRod System'.'Autonomous Vehicle (AV) System'.'Steering Control';
                            perform 'eRod_Autonomous_Vehicle_2024 Project'::'eRod_Autonomous_Vehicle_2024'::'Logical Architecture'::'Logical Functions'::'Root Logical Function'.'Automatic Steer' ; 
                            ref :>> ownedFunctionalAllocation =  ('eRod_Autonomous_Vehicle_2024 Project'::'eRod_Autonomous_Vehicle_2024'::'Logical Architecture'::'Structure'::'eRod System'.'Autonomous Vehicle (AV) System'.'Steering Control'.'5b1fcd96-e5d3-4fc4-a2f1-aa0d6247a36b'); 
                        }  
                        ref :>> ownedFunctionalAllocation =  ('eRod_Autonomous_Vehicle_2024 Project'::'eRod_Autonomous_Vehicle_2024'::'Logical Architecture'::'Structure'::'eRod System'.'Autonomous Vehicle (AV) System'.'f6756e54-863a-403d-b1c2-715cd1d350f7'); 
                        ref :>> ownedLogicalComponents =  ('eRod_Autonomous_Vehicle_2024 Project'::'eRod_Autonomous_Vehicle_2024'::'Logical Architecture'::'Structure'::'eRod System'.'Autonomous Vehicle (AV) System'.'Perception',
                        'eRod_Autonomous_Vehicle_2024 Project'::'eRod_Autonomous_Vehicle_2024'::'Logical Architecture'::'Structure'::'eRod System'.'Autonomous Vehicle (AV) System'.'Auto Drive',
                        'eRod_Autonomous_Vehicle_2024 Project'::'eRod_Autonomous_Vehicle_2024'::'Logical Architecture'::'Structure'::'eRod System'.'Autonomous Vehicle (AV) System'.'Park Assist',
                        'eRod_Autonomous_Vehicle_2024 Project'::'eRod_Autonomous_Vehicle_2024'::'Logical Architecture'::'Structure'::'eRod System'.'Autonomous Vehicle (AV) System'.'Mapping',
                        'eRod_Autonomous_Vehicle_2024 Project'::'eRod_Autonomous_Vehicle_2024'::'Logical Architecture'::'Structure'::'eRod System'.'Autonomous Vehicle (AV) System'.'Accell Control',
                        'eRod_Autonomous_Vehicle_2024 Project'::'eRod_Autonomous_Vehicle_2024'::'Logical Architecture'::'Structure'::'eRod System'.'Autonomous Vehicle (AV) System'.'Steering Control'); 
                    }  
                    part 'Suspension' : LogicalComponent { 
                        @CapellaID { eid = "b7a2a428-ee9f-47be-86db-9a022e6f54c9"; } 
                        attribute :>> isAbstract = false; 
                        attribute :>> isActor = false; 
                        attribute :>> isHuman = false; 
                        allocation '9706d001-afbd-4b29-9323-bcdedb1dc41f' : ComponentFunctionalAllocation
                            allocate function ::> 'eRod_Autonomous_Vehicle_2024 Project'::'eRod_Autonomous_Vehicle_2024'::'Logical Architecture'::'Logical Functions'::'Root Logical Function'.'Absorb bumps in the road'
                            to component ::> 'eRod_Autonomous_Vehicle_2024 Project'::'eRod_Autonomous_Vehicle_2024'::'Logical Architecture'::'Structure'::'eRod System'.'Suspension';
                        perform 'eRod_Autonomous_Vehicle_2024 Project'::'eRod_Autonomous_Vehicle_2024'::'Logical Architecture'::'Logical Functions'::'Root Logical Function'.'Absorb bumps in the road' ; 
                        allocation '451723a8-dafa-4a53-a9f8-2052f4b72405' : ComponentFunctionalAllocation
                            allocate function ::> 'eRod_Autonomous_Vehicle_2024 Project'::'eRod_Autonomous_Vehicle_2024'::'Logical Architecture'::'Logical Functions'::'Root Logical Function'.'Maximize the friction between the tires and roads'
                            to component ::> 'eRod_Autonomous_Vehicle_2024 Project'::'eRod_Autonomous_Vehicle_2024'::'Logical Architecture'::'Structure'::'eRod System'.'Suspension';
                        perform 'eRod_Autonomous_Vehicle_2024 Project'::'eRod_Autonomous_Vehicle_2024'::'Logical Architecture'::'Logical Functions'::'Root Logical Function'.'Maximize the friction between the tires and roads' ; 
                        ref :>> ownedFunctionalAllocation =  ('eRod_Autonomous_Vehicle_2024 Project'::'eRod_Autonomous_Vehicle_2024'::'Logical Architecture'::'Structure'::'eRod System'.'Suspension'.'9706d001-afbd-4b29-9323-bcdedb1dc41f',
                        'eRod_Autonomous_Vehicle_2024 Project'::'eRod_Autonomous_Vehicle_2024'::'Logical Architecture'::'Structure'::'eRod System'.'Suspension'.'451723a8-dafa-4a53-a9f8-2052f4b72405'); 
                    }  
                    part 'Frame' : LogicalComponent { 
                        @CapellaID { eid = "779e2f3b-5d92-4d91-9b55-dec30fe2fee5"; } 
                        attribute :>> isAbstract = false; 
                        attribute :>> isActor = false; 
                        attribute :>> isHuman = false; 
                    }  
                    part 'Sensors' : LogicalComponent { 
                        @CapellaID { eid = "c74ac977-7f8a-4e41-8860-38b8d207e003"; } 
                        attribute :>> isAbstract = false; 
                        attribute :>> isActor = false; 
                        attribute :>> isHuman = false; 
                        part 'Camera' : LogicalComponent { 
                            @CapellaID { eid = "cff2098d-29bd-4a0a-8cad-462b2b926188"; } 
                            attribute :>> isAbstract = false; 
                            attribute :>> isActor = false; 
                            attribute :>> isHuman = false; 
                            allocation 'ae79ba13-a2ce-400e-9b06-ab5e111500b6' : ComponentFunctionalAllocation
                                allocate function ::> 'eRod_Autonomous_Vehicle_2024 Project'::'eRod_Autonomous_Vehicle_2024'::'Logical Architecture'::'Logical Functions'::'Root Logical Function'.'Detect road'.'Capture view'
                                to component ::> 'eRod_Autonomous_Vehicle_2024 Project'::'eRod_Autonomous_Vehicle_2024'::'Logical Architecture'::'Structure'::'eRod System'.'Sensors'.'Camera';
                            perform 'eRod_Autonomous_Vehicle_2024 Project'::'eRod_Autonomous_Vehicle_2024'::'Logical Architecture'::'Logical Functions'::'Root Logical Function'.'Detect road'.'Capture view' ; 
                            ref :>> ownedFunctionalAllocation =  ('eRod_Autonomous_Vehicle_2024 Project'::'eRod_Autonomous_Vehicle_2024'::'Logical Architecture'::'Structure'::'eRod System'.'Sensors'.'Camera'.'ae79ba13-a2ce-400e-9b06-ab5e111500b6'); 
                        }  
                        part 'Lidar' : LogicalComponent { 
                            @CapellaID { eid = "08f58737-8ca4-4207-a8f9-f74d4f7c0360"; } 
                            attribute :>> isAbstract = false; 
                            attribute :>> isActor = false; 
                            attribute :>> isHuman = false; 
                            allocation '8021f59a-df50-48c4-b123-9982e6dd0a02' : ComponentFunctionalAllocation
                                allocate function ::> 'eRod_Autonomous_Vehicle_2024 Project'::'eRod_Autonomous_Vehicle_2024'::'Logical Architecture'::'Logical Functions'::'Root Logical Function'.'Capture points'
                                to component ::> 'eRod_Autonomous_Vehicle_2024 Project'::'eRod_Autonomous_Vehicle_2024'::'Logical Architecture'::'Structure'::'eRod System'.'Sensors'.'Lidar';
                            perform 'eRod_Autonomous_Vehicle_2024 Project'::'eRod_Autonomous_Vehicle_2024'::'Logical Architecture'::'Logical Functions'::'Root Logical Function'.'Capture points' ; 
                            ref :>> ownedFunctionalAllocation =  ('eRod_Autonomous_Vehicle_2024 Project'::'eRod_Autonomous_Vehicle_2024'::'Logical Architecture'::'Structure'::'eRod System'.'Sensors'.'Lidar'.'8021f59a-df50-48c4-b123-9982e6dd0a02'); 
                        }  
                        part 'Radar' : LogicalComponent { 
                            @CapellaID { eid = "187ff384-31e9-4ade-b32f-203a7b0f354a"; } 
                            attribute :>> isAbstract = false; 
                            attribute :>> isActor = false; 
                            attribute :>> isHuman = false; 
                            allocation 'c124a546-1be4-4faf-88b7-585818da1a40' : ComponentFunctionalAllocation
                                allocate function ::> 'eRod_Autonomous_Vehicle_2024 Project'::'eRod_Autonomous_Vehicle_2024'::'Logical Architecture'::'Logical Functions'::'Root Logical Function'.'Capture radar echo'
                                to component ::> 'eRod_Autonomous_Vehicle_2024 Project'::'eRod_Autonomous_Vehicle_2024'::'Logical Architecture'::'Structure'::'eRod System'.'Sensors'.'Radar';
                            perform 'eRod_Autonomous_Vehicle_2024 Project'::'eRod_Autonomous_Vehicle_2024'::'Logical Architecture'::'Logical Functions'::'Root Logical Function'.'Capture radar echo' ; 
                            ref :>> ownedFunctionalAllocation =  ('eRod_Autonomous_Vehicle_2024 Project'::'eRod_Autonomous_Vehicle_2024'::'Logical Architecture'::'Structure'::'eRod System'.'Sensors'.'Radar'.'c124a546-1be4-4faf-88b7-585818da1a40'); 
                        }  
                        ref :>> ownedLogicalComponents =  ('eRod_Autonomous_Vehicle_2024 Project'::'eRod_Autonomous_Vehicle_2024'::'Logical Architecture'::'Structure'::'eRod System'.'Sensors'.'Camera',
                        'eRod_Autonomous_Vehicle_2024 Project'::'eRod_Autonomous_Vehicle_2024'::'Logical Architecture'::'Structure'::'eRod System'.'Sensors'.'Lidar',
                        'eRod_Autonomous_Vehicle_2024 Project'::'eRod_Autonomous_Vehicle_2024'::'Logical Architecture'::'Structure'::'eRod System'.'Sensors'.'Radar'); 
                    }  
                    part 'Vehicle Control Module' : LogicalComponent { 
                        @CapellaID { eid = "efd3ce11-eefb-4182-92fc-15b69f6723b4"; } 
                        attribute :>> isAbstract = false; 
                        attribute :>> isActor = false; 
                        attribute :>> isHuman = false; 
                        allocation '0d622bc8-3275-4efb-9e79-0a89ed385722' : ComponentFunctionalAllocation
                            allocate function ::> 'eRod_Autonomous_Vehicle_2024 Project'::'eRod_Autonomous_Vehicle_2024'::'Logical Architecture'::'Logical Functions'::'Root Logical Function'.'remote update'
                            to component ::> 'eRod_Autonomous_Vehicle_2024 Project'::'eRod_Autonomous_Vehicle_2024'::'Logical Architecture'::'Structure'::'eRod System'.'Vehicle Control Module';
                        perform 'eRod_Autonomous_Vehicle_2024 Project'::'eRod_Autonomous_Vehicle_2024'::'Logical Architecture'::'Logical Functions'::'Root Logical Function'.'remote update' ; 
                        allocation '3684e02a-e70d-4d21-b092-9eebc18a54cc' : ComponentFunctionalAllocation
                            allocate function ::> 'eRod_Autonomous_Vehicle_2024 Project'::'eRod_Autonomous_Vehicle_2024'::'Logical Architecture'::'Logical Functions'::'Root Logical Function'.'Improve motor performance'
                            to component ::> 'eRod_Autonomous_Vehicle_2024 Project'::'eRod_Autonomous_Vehicle_2024'::'Logical Architecture'::'Structure'::'eRod System'.'Vehicle Control Module';
                        perform 'eRod_Autonomous_Vehicle_2024 Project'::'eRod_Autonomous_Vehicle_2024'::'Logical Architecture'::'Logical Functions'::'Root Logical Function'.'Improve motor performance' ; 
                        allocation 'fe14b6f0-63e9-49ca-811b-eaf4fc5eadb9' : ComponentFunctionalAllocation
                            allocate function ::> 'eRod_Autonomous_Vehicle_2024 Project'::'eRod_Autonomous_Vehicle_2024'::'Logical Architecture'::'Logical Functions'::'Root Logical Function'.'connected to the center'
                            to component ::> 'eRod_Autonomous_Vehicle_2024 Project'::'eRod_Autonomous_Vehicle_2024'::'Logical Architecture'::'Structure'::'eRod System'.'Vehicle Control Module';
                        perform 'eRod_Autonomous_Vehicle_2024 Project'::'eRod_Autonomous_Vehicle_2024'::'Logical Architecture'::'Logical Functions'::'Root Logical Function'.'connected to the center' ; 
                        ref :>> ownedFunctionalAllocation =  ('eRod_Autonomous_Vehicle_2024 Project'::'eRod_Autonomous_Vehicle_2024'::'Logical Architecture'::'Structure'::'eRod System'.'Vehicle Control Module'.'0d622bc8-3275-4efb-9e79-0a89ed385722',
                        'eRod_Autonomous_Vehicle_2024 Project'::'eRod_Autonomous_Vehicle_2024'::'Logical Architecture'::'Structure'::'eRod System'.'Vehicle Control Module'.'3684e02a-e70d-4d21-b092-9eebc18a54cc',
                        'eRod_Autonomous_Vehicle_2024 Project'::'eRod_Autonomous_Vehicle_2024'::'Logical Architecture'::'Structure'::'eRod System'.'Vehicle Control Module'.'fe14b6f0-63e9-49ca-811b-eaf4fc5eadb9'); 
                    }  
                    part 'LC 12' : LogicalComponent { 
                        @CapellaID { eid = "97daa025-1a35-4280-aead-e2f7971bee32"; } 
                        attribute :>> isAbstract = false; 
                        attribute :>> isActor = false; 
                        attribute :>> isHuman = false; 
                    }  
                    part 'Drive Pilot App' : LogicalComponent { 
                        @CapellaID { eid = "c26051ef-4609-45cf-8711-9ddb38f2d887"; } 
                        attribute :>> isAbstract = false; 
                        attribute :>> isActor = false; 
                        attribute :>> isHuman = false; 
                        allocation '66cc0ad0-a9f9-4f5a-b3f4-e7a98b1966f8' : ComponentFunctionalAllocation
                            allocate function ::> 'eRod_Autonomous_Vehicle_2024 Project'::'eRod_Autonomous_Vehicle_2024'::'Logical Architecture'::'Logical Functions'::'Root Logical Function'.'Remote Operate Car'
                            to component ::> 'eRod_Autonomous_Vehicle_2024 Project'::'eRod_Autonomous_Vehicle_2024'::'Logical Architecture'::'Structure'::'eRod System'.'Drive Pilot App';
                        perform 'eRod_Autonomous_Vehicle_2024 Project'::'eRod_Autonomous_Vehicle_2024'::'Logical Architecture'::'Logical Functions'::'Root Logical Function'.'Remote Operate Car' ; 
                        ref :>> ownedFunctionalAllocation =  ('eRod_Autonomous_Vehicle_2024 Project'::'eRod_Autonomous_Vehicle_2024'::'Logical Architecture'::'Structure'::'eRod System'.'Drive Pilot App'.'66cc0ad0-a9f9-4f5a-b3f4-e7a98b1966f8'); 
                    }  
                    part 'GPS' : LogicalComponent { 
                        @CapellaID { eid = "f88bac01-3236-414e-a750-f13a69ef7a5b"; } 
                        attribute :>> isAbstract = false; 
                        attribute :>> isActor = false; 
                        attribute :>> isHuman = false; 
                    }  
                    part 'Bluetooth Interface' : LogicalComponent { 
                        @CapellaID { eid = "505bf2fd-ad27-4852-8ca2-9a910cbed643"; } 
                        attribute :>> isAbstract = false; 
                        attribute :>> isActor = false; 
                        attribute :>> isHuman = false; 
                    }  
                    state 'StateMachine 1' : StateMachine  { 
                        @CapellaID { eid = "b613328c-df78-478d-a389-1e2b22a72b26"; } 
                        attribute :>> isControlOperator = false; 
                        state 'Sporty drive, without software update' : State  { 
                            @CapellaID { eid = "6a692357-8eaa-4ee9-9ff3-38331b1fb6e9"; } 
                        }  
                        state 'sporty drive, with software update' : State  { 
                            @CapellaID { eid = "72f3b051-dfe2-42f7-bb87-028d6566d411"; } 
                        }  
                        state 'Choice  4' : ChoicePseudoState { 
                            @CapellaID { eid = "7f75a847-b5d1-459a-899d-bef9b70a35bc"; } 
                        }  
                        state 'Temperature reached limit' : State  { 
                            @CapellaID { eid = "958727eb-bdb1-49ab-8f86-d8e69075c703"; } 
                            ref :>> doActivity =  ('eRod_Autonomous_Vehicle_2024 Project'::'eRod_Autonomous_Vehicle_2024'::'Logical Architecture'::'Logical Functions'::'Root Logical Function'.'Motor protect'.'Monitor temperature'); 
                        }  
                        state 'Power loss' : State  { 
                            @CapellaID { eid = "a214e8ad-3d38-4996-adc6-374fa106c9d5"; } 
                            ref :>> doActivity =  ('eRod_Autonomous_Vehicle_2024 Project'::'eRod_Autonomous_Vehicle_2024'::'Logical Architecture'::'Logical Functions'::'Root Logical Function'.'Motor protect'.'Reduce power'); 
                        }  
                        state 'Deacceleration' : State  { 
                            @CapellaID { eid = "001723a4-a68c-4721-a271-c980141f706a"; } 
                        }  
                        state 'Stop' : State  { 
                            @CapellaID { eid = "eb8c1da6-2a1f-4f98-9bd6-b1261b0b9aa6"; } 
                        }  
                        state 'Car racing experience absorbed' : State  { 
                            @CapellaID { eid = "2a8514c2-b416-4184-af51-67504df17595"; } 
                        }  
                        state 'Display overheating warning' : State  { 
                            @CapellaID { eid = "4704d160-3b6a-41ed-9912-1eb9aa1bf304"; } 
                        }  
                        state 'Fork  11' : ForkPseudoState { 
                            @CapellaID { eid = "b2295be7-d4d1-46d5-923d-d8be4b6ff511"; } 
                        }  
                        state 'Driver get informed and report issues' : State  { 
                            @CapellaID { eid = "c9c60e20-8acc-41e2-97ef-71c911506e59"; } 
                        }  
                        state 'Terminate' : TerminatePseudoState { 
                            @CapellaID { eid = "3c0920f2-3ed0-44cd-aea0-bad1870f662f"; } 
                        }  
                        state 'Final' : FinalState { 
                            @CapellaID { eid = "b0e1eee0-080c-46ff-9ed1-7447660af853"; } 
                        }  
                        state 'Temperature under controlled, no overheating issues' : State  { 
                            @CapellaID { eid = "3cf46a8b-a78a-41b0-8f12-7a2f35f2ce78"; } 
                            ref :>> doActivity =  ('eRod_Autonomous_Vehicle_2024 Project'::'eRod_Autonomous_Vehicle_2024'::'Logical Architecture'::'Logical Functions'::'Root Logical Function'.'Control temperature'.'Limit power'); 
                        }  
                        state 'Driver obtain whole car racing experience' : State  { 
                            @CapellaID { eid = "f0361898-290c-4be0-a103-04438ac03dcf"; } 
                        }  
                        state 'Final ' : FinalState { 
                            @CapellaID { eid = "af25aebc-8904-4266-9754-6963a050b12b"; } 
                        }  
                        state 'Fork' : ForkPseudoState { 
                            @CapellaID { eid = "801f1f35-b8aa-40ab-8330-1701cbde8434"; } 
                        }  
                        state 'Still capable to finish car racing' : State  { 
                            @CapellaID { eid = "ea3bf645-3ed6-4573-998e-9d1e95c650a0"; } 
                        }  
                        state 'Join' : JoinPseudoState { 
                            @CapellaID { eid = "477c6557-aaec-4017-9dbc-52c5593afd27"; } 
                        }  
                        entry; then 'Choice  4';  
                        transition 'cfaa5377-8e97-4863-ac2a-a1142040156b' 
                            first 'eRod_Autonomous_Vehicle_2024 Project'::'eRod_Autonomous_Vehicle_2024'::'Logical Architecture'::'Structure'::'eRod System'.'StateMachine 1'.'Choice  4'
                            then 'eRod_Autonomous_Vehicle_2024 Project'::'eRod_Autonomous_Vehicle_2024'::'Logical Architecture'::'Structure'::'eRod System'.'StateMachine 1'.'Sporty drive, without software update' {
                        }  
                        transition 'ab008b8f-6c7b-4f48-8bbe-411e8fea44a9' 
                            first 'eRod_Autonomous_Vehicle_2024 Project'::'eRod_Autonomous_Vehicle_2024'::'Logical Architecture'::'Structure'::'eRod System'.'StateMachine 1'.'Choice  4'
                            then 'eRod_Autonomous_Vehicle_2024 Project'::'eRod_Autonomous_Vehicle_2024'::'Logical Architecture'::'Structure'::'eRod System'.'StateMachine 1'.'sporty drive, with software update' {
                        }  
                        transition 'e08bbab9-aafd-4948-929a-451f8bbefff8' 
                            first 'eRod_Autonomous_Vehicle_2024 Project'::'eRod_Autonomous_Vehicle_2024'::'Logical Architecture'::'Structure'::'eRod System'.'StateMachine 1'.'Sporty drive, without software update'
                            accept 'ef57735d-e98b-466c-be56-d8fbca4ab801' :> 'eRod_Autonomous_Vehicle_2024 Project'::'eRod_Autonomous_Vehicle_2024'::'Logical Architecture'::'Logical Functions'::'Root Logical Function'.'Motor protect'.'ef57735d-e98b-466c-be56-d8fbca4ab801'
                            then 'eRod_Autonomous_Vehicle_2024 Project'::'eRod_Autonomous_Vehicle_2024'::'Logical Architecture'::'Structure'::'eRod System'.'StateMachine 1'.'Temperature reached limit' {
                        }  
                        transition 'b5af38f6-de6a-4dad-a326-64f65e136be8' 
                            first 'eRod_Autonomous_Vehicle_2024 Project'::'eRod_Autonomous_Vehicle_2024'::'Logical Architecture'::'Structure'::'eRod System'.'StateMachine 1'.'Temperature reached limit'
                            then 'eRod_Autonomous_Vehicle_2024 Project'::'eRod_Autonomous_Vehicle_2024'::'Logical Architecture'::'Structure'::'eRod System'.'StateMachine 1'.'Fork  11' {
                        }  
                        transition '41fb67ce-a2d0-44dc-bd5f-e90a25485a05' 
                            first 'eRod_Autonomous_Vehicle_2024 Project'::'eRod_Autonomous_Vehicle_2024'::'Logical Architecture'::'Structure'::'eRod System'.'StateMachine 1'.'Power loss'
                            accept '19d12ee0-70a6-49d7-9468-396730331e38' :> 'eRod_Autonomous_Vehicle_2024 Project'::'eRod_Autonomous_Vehicle_2024'::'Logical Architecture'::'Logical Functions'::'Root Logical Function'.'19d12ee0-70a6-49d7-9468-396730331e38'
                            then 'eRod_Autonomous_Vehicle_2024 Project'::'eRod_Autonomous_Vehicle_2024'::'Logical Architecture'::'Structure'::'eRod System'.'StateMachine 1'.'Deacceleration' {
                        }  
                        transition 'b5650c26-4496-44bb-95e6-c7358ec420e6' 
                            first 'eRod_Autonomous_Vehicle_2024 Project'::'eRod_Autonomous_Vehicle_2024'::'Logical Architecture'::'Structure'::'eRod System'.'StateMachine 1'.'Deacceleration'
                            then 'eRod_Autonomous_Vehicle_2024 Project'::'eRod_Autonomous_Vehicle_2024'::'Logical Architecture'::'Structure'::'eRod System'.'StateMachine 1'.'Stop' {
                        }  
                        transition 'daee97ab-b877-48bb-bdb4-8b99bccb861c' 
                            first 'eRod_Autonomous_Vehicle_2024 Project'::'eRod_Autonomous_Vehicle_2024'::'Logical Architecture'::'Structure'::'eRod System'.'StateMachine 1'.'Stop'
                            then 'eRod_Autonomous_Vehicle_2024 Project'::'eRod_Autonomous_Vehicle_2024'::'Logical Architecture'::'Structure'::'eRod System'.'StateMachine 1'.'Car racing experience absorbed' {
                        }  
                        transition '7e39e57c-8845-49b2-a57f-62c19c03ed3b' 
                            first 'eRod_Autonomous_Vehicle_2024 Project'::'eRod_Autonomous_Vehicle_2024'::'Logical Architecture'::'Structure'::'eRod System'.'StateMachine 1'.'Fork  11'
                            accept '57378bfd-1c57-40f3-a130-a89cc2cc13d8' :> 'eRod_Autonomous_Vehicle_2024 Project'::'eRod_Autonomous_Vehicle_2024'::'Logical Architecture'::'Logical Functions'::'Root Logical Function'.'Motor protect'.'57378bfd-1c57-40f3-a130-a89cc2cc13d8'
                            then 'eRod_Autonomous_Vehicle_2024 Project'::'eRod_Autonomous_Vehicle_2024'::'Logical Architecture'::'Structure'::'eRod System'.'StateMachine 1'.'Power loss' {
                        }  
                        transition '43ffb987-00ec-4b69-8d90-bc202c8a8ef0' 
                            first 'eRod_Autonomous_Vehicle_2024 Project'::'eRod_Autonomous_Vehicle_2024'::'Logical Architecture'::'Structure'::'eRod System'.'StateMachine 1'.'Fork  11'
                            accept '76b26dd2-2a46-4b84-b303-1c3132586ce4' :> 'eRod_Autonomous_Vehicle_2024 Project'::'eRod_Autonomous_Vehicle_2024'::'Logical Architecture'::'Logical Functions'::'Root Logical Function'.'76b26dd2-2a46-4b84-b303-1c3132586ce4'
                            then 'eRod_Autonomous_Vehicle_2024 Project'::'eRod_Autonomous_Vehicle_2024'::'Logical Architecture'::'Structure'::'eRod System'.'StateMachine 1'.'Display overheating warning' {
                        }  
                        transition '43b7abe5-952d-41cc-adae-18bf76515f6d' 
                            first 'eRod_Autonomous_Vehicle_2024 Project'::'eRod_Autonomous_Vehicle_2024'::'Logical Architecture'::'Structure'::'eRod System'.'StateMachine 1'.'Display overheating warning'
                            then 'eRod_Autonomous_Vehicle_2024 Project'::'eRod_Autonomous_Vehicle_2024'::'Logical Architecture'::'Structure'::'eRod System'.'StateMachine 1'.'Driver get informed and report issues' {
                        }  
                        transition 'c5d6712d-2c22-4bfd-89ae-6c6b5e6d46e1' 
                            first 'eRod_Autonomous_Vehicle_2024 Project'::'eRod_Autonomous_Vehicle_2024'::'Logical Architecture'::'Structure'::'eRod System'.'StateMachine 1'.'Driver get informed and report issues'
                            then 'eRod_Autonomous_Vehicle_2024 Project'::'eRod_Autonomous_Vehicle_2024'::'Logical Architecture'::'Structure'::'eRod System'.'StateMachine 1'.'Final' {
                        }  
                        transition '321cfe47-663f-4098-95dd-66178f5532b0' 
                            first 'eRod_Autonomous_Vehicle_2024 Project'::'eRod_Autonomous_Vehicle_2024'::'Logical Architecture'::'Structure'::'eRod System'.'StateMachine 1'.'sporty drive, with software update'
                            then 'eRod_Autonomous_Vehicle_2024 Project'::'eRod_Autonomous_Vehicle_2024'::'Logical Architecture'::'Structure'::'eRod System'.'StateMachine 1'.'Fork' {
                        }  
                        transition '7980179e-4ec2-459b-a557-7ddd45b247d1' 
                            first 'eRod_Autonomous_Vehicle_2024 Project'::'eRod_Autonomous_Vehicle_2024'::'Logical Architecture'::'Structure'::'eRod System'.'StateMachine 1'.'Temperature under controlled, no overheating issues'
                            then 'eRod_Autonomous_Vehicle_2024 Project'::'eRod_Autonomous_Vehicle_2024'::'Logical Architecture'::'Structure'::'eRod System'.'StateMachine 1'.'Join' {
                        }  
                        transition 'ed020874-31e8-4a4a-a1ff-ba4454810c65' 
                            first 'eRod_Autonomous_Vehicle_2024 Project'::'eRod_Autonomous_Vehicle_2024'::'Logical Architecture'::'Structure'::'eRod System'.'StateMachine 1'.'Driver obtain whole car racing experience'
                            then 'eRod_Autonomous_Vehicle_2024 Project'::'eRod_Autonomous_Vehicle_2024'::'Logical Architecture'::'Structure'::'eRod System'.'StateMachine 1'.'Final ' {
                        }  
                        transition '9f798fea-272c-4696-8f5a-056204340f97' 
                            first 'eRod_Autonomous_Vehicle_2024 Project'::'eRod_Autonomous_Vehicle_2024'::'Logical Architecture'::'Structure'::'eRod System'.'StateMachine 1'.'Car racing experience absorbed'
                            then 'eRod_Autonomous_Vehicle_2024 Project'::'eRod_Autonomous_Vehicle_2024'::'Logical Architecture'::'Structure'::'eRod System'.'StateMachine 1'.'Terminate' {
                        }  
                        transition 'ba607497-5040-4911-a090-5b1ce48257ad' 
                            first 'eRod_Autonomous_Vehicle_2024 Project'::'eRod_Autonomous_Vehicle_2024'::'Logical Architecture'::'Structure'::'eRod System'.'StateMachine 1'.'Fork'
                            then 'eRod_Autonomous_Vehicle_2024 Project'::'eRod_Autonomous_Vehicle_2024'::'Logical Architecture'::'Structure'::'eRod System'.'StateMachine 1'.'Temperature under controlled, no overheating issues' {
                        }  
                        transition 'fe14c08f-00cd-4bd8-893e-b3785a4d88e5' 
                            first 'eRod_Autonomous_Vehicle_2024 Project'::'eRod_Autonomous_Vehicle_2024'::'Logical Architecture'::'Structure'::'eRod System'.'StateMachine 1'.'Fork'
                            then 'eRod_Autonomous_Vehicle_2024 Project'::'eRod_Autonomous_Vehicle_2024'::'Logical Architecture'::'Structure'::'eRod System'.'StateMachine 1'.'Still capable to finish car racing' {
                        }  
                        transition '26633e65-d7ac-481a-bbbd-b4ae8805520b' 
                            first 'eRod_Autonomous_Vehicle_2024 Project'::'eRod_Autonomous_Vehicle_2024'::'Logical Architecture'::'Structure'::'eRod System'.'StateMachine 1'.'Still capable to finish car racing'
                            then 'eRod_Autonomous_Vehicle_2024 Project'::'eRod_Autonomous_Vehicle_2024'::'Logical Architecture'::'Structure'::'eRod System'.'StateMachine 1'.'Join' {
                        }  
                        transition '6ce1a296-9537-4711-886f-0ec52faf0c66' 
                            first 'eRod_Autonomous_Vehicle_2024 Project'::'eRod_Autonomous_Vehicle_2024'::'Logical Architecture'::'Structure'::'eRod System'.'StateMachine 1'.'Join'
                            then 'eRod_Autonomous_Vehicle_2024 Project'::'eRod_Autonomous_Vehicle_2024'::'Logical Architecture'::'Structure'::'eRod System'.'StateMachine 1'.'Driver obtain whole car racing experience' {
                        }  
                    }  
                    ref :>> ownedFunctionalAllocation =  ('eRod_Autonomous_Vehicle_2024 Project'::'eRod_Autonomous_Vehicle_2024'::'Logical Architecture'::'Structure'::'eRod System'.'48d70b70-2342-4858-b6ec-7de8102695d6',
                    'eRod_Autonomous_Vehicle_2024 Project'::'eRod_Autonomous_Vehicle_2024'::'Logical Architecture'::'Structure'::'eRod System'.'f7b18b86-989d-4ab7-9697-f0f6aef56147',
                    'eRod_Autonomous_Vehicle_2024 Project'::'eRod_Autonomous_Vehicle_2024'::'Logical Architecture'::'Structure'::'eRod System'.'0a479dbb-a597-4f28-8629-99b63efade93',
                    'eRod_Autonomous_Vehicle_2024 Project'::'eRod_Autonomous_Vehicle_2024'::'Logical Architecture'::'Structure'::'eRod System'.'da5f5810-e58c-403b-919e-118cf118fe09',
                    'eRod_Autonomous_Vehicle_2024 Project'::'eRod_Autonomous_Vehicle_2024'::'Logical Architecture'::'Structure'::'eRod System'.'447a813a-c372-45f1-8285-fc3cc1077fe6'); 
                    ref :>> ownedComponentExchanges =  ('eRod_Autonomous_Vehicle_2024 Project'::'eRod_Autonomous_Vehicle_2024'::'Logical Architecture'::'Structure'::'eRod System'.'c097bdf7-2737-4cf6-b21d-b8a04bdf7027',
                    'eRod_Autonomous_Vehicle_2024 Project'::'eRod_Autonomous_Vehicle_2024'::'Logical Architecture'::'Structure'::'eRod System'.'6800b945-167d-41f6-bc15-64e1ce776702',
                    'eRod_Autonomous_Vehicle_2024 Project'::'eRod_Autonomous_Vehicle_2024'::'Logical Architecture'::'Structure'::'eRod System'.'e341d16c-5a6f-4b0b-9051-c75525d48151',
                    'eRod_Autonomous_Vehicle_2024 Project'::'eRod_Autonomous_Vehicle_2024'::'Logical Architecture'::'Structure'::'eRod System'.'ec8c564d-cc27-403a-b6de-c2ed7ed23a17'); 
                    ref :>> ownedLogicalComponents =  ('eRod_Autonomous_Vehicle_2024 Project'::'eRod_Autonomous_Vehicle_2024'::'Logical Architecture'::'Structure'::'eRod System'.'Auxiliary Consumers',
                    'eRod_Autonomous_Vehicle_2024 Project'::'eRod_Autonomous_Vehicle_2024'::'Logical Architecture'::'Structure'::'eRod System'.'Powertrain',
                    'eRod_Autonomous_Vehicle_2024 Project'::'eRod_Autonomous_Vehicle_2024'::'Logical Architecture'::'Structure'::'eRod System'.'Steering System',
                    'eRod_Autonomous_Vehicle_2024 Project'::'eRod_Autonomous_Vehicle_2024'::'Logical Architecture'::'Structure'::'eRod System'.'Brake System',
                    'eRod_Autonomous_Vehicle_2024 Project'::'eRod_Autonomous_Vehicle_2024'::'Logical Architecture'::'Structure'::'eRod System'.'Battery System',
                    'eRod_Autonomous_Vehicle_2024 Project'::'eRod_Autonomous_Vehicle_2024'::'Logical Architecture'::'Structure'::'eRod System'.'Lights',
                    'eRod_Autonomous_Vehicle_2024 Project'::'eRod_Autonomous_Vehicle_2024'::'Logical Architecture'::'Structure'::'eRod System'.'Autonomous Vehicle (AV) System',
                    'eRod_Autonomous_Vehicle_2024 Project'::'eRod_Autonomous_Vehicle_2024'::'Logical Architecture'::'Structure'::'eRod System'.'Suspension',
                    'eRod_Autonomous_Vehicle_2024 Project'::'eRod_Autonomous_Vehicle_2024'::'Logical Architecture'::'Structure'::'eRod System'.'Frame',
                    'eRod_Autonomous_Vehicle_2024 Project'::'eRod_Autonomous_Vehicle_2024'::'Logical Architecture'::'Structure'::'eRod System'.'Sensors',
                    'eRod_Autonomous_Vehicle_2024 Project'::'eRod_Autonomous_Vehicle_2024'::'Logical Architecture'::'Structure'::'eRod System'.'Vehicle Control Module',
                    'eRod_Autonomous_Vehicle_2024 Project'::'eRod_Autonomous_Vehicle_2024'::'Logical Architecture'::'Structure'::'eRod System'.'LC 12',
                    'eRod_Autonomous_Vehicle_2024 Project'::'eRod_Autonomous_Vehicle_2024'::'Logical Architecture'::'Structure'::'eRod System'.'Drive Pilot App',
                    'eRod_Autonomous_Vehicle_2024 Project'::'eRod_Autonomous_Vehicle_2024'::'Logical Architecture'::'Structure'::'eRod System'.'GPS',
                    'eRod_Autonomous_Vehicle_2024 Project'::'eRod_Autonomous_Vehicle_2024'::'Logical Architecture'::'Structure'::'eRod System'.'Bluetooth Interface'); 
                    ref :>> ownedStateMachines =  ('eRod_Autonomous_Vehicle_2024 Project'::'eRod_Autonomous_Vehicle_2024'::'Logical Architecture'::'Structure'::'eRod System'.'StateMachine 1'); 
                     
                }  
                part 'Driver' : LogicalComponent { 
                    @CapellaID { eid = "6d831985-2e2a-4f34-8356-625b9836a5cf"; } 
                    attribute :>> isAbstract = false; 
                    attribute :>> isActor = true; 
                    attribute :>> isHuman = true; 
                    allocation '66c977fd-603b-4c73-9075-d7173e0cbb23' : ComponentFunctionalAllocation
                        allocate function ::> 'eRod_Autonomous_Vehicle_2024 Project'::'eRod_Autonomous_Vehicle_2024'::'Logical Architecture'::'Logical Functions'::'Root Logical Function'.'Drive on a race track'
                        to component ::> 'eRod_Autonomous_Vehicle_2024 Project'::'eRod_Autonomous_Vehicle_2024'::'Logical Architecture'::'Structure'::'Driver';
                    perform 'eRod_Autonomous_Vehicle_2024 Project'::'eRod_Autonomous_Vehicle_2024'::'Logical Architecture'::'Logical Functions'::'Root Logical Function'.'Drive on a race track' ; 
                    allocation '1bd9afe0-ac5a-4c75-bc0f-c6b8a3fcc88a' : ComponentFunctionalAllocation
                        allocate function ::> 'eRod_Autonomous_Vehicle_2024 Project'::'eRod_Autonomous_Vehicle_2024'::'Logical Architecture'::'Logical Functions'::'Root Logical Function'.'Car racing experience absorbed'
                        to component ::> 'eRod_Autonomous_Vehicle_2024 Project'::'eRod_Autonomous_Vehicle_2024'::'Logical Architecture'::'Structure'::'Driver';
                    perform 'eRod_Autonomous_Vehicle_2024 Project'::'eRod_Autonomous_Vehicle_2024'::'Logical Architecture'::'Logical Functions'::'Root Logical Function'.'Car racing experience absorbed' ; 
                    allocation 'de99e26b-62cb-4a6e-9fa9-8b10996b826f' : ComponentFunctionalAllocation
                        allocate function ::> 'eRod_Autonomous_Vehicle_2024 Project'::'eRod_Autonomous_Vehicle_2024'::'Logical Architecture'::'Logical Functions'::'Root Logical Function'.'Report issues'
                        to component ::> 'eRod_Autonomous_Vehicle_2024 Project'::'eRod_Autonomous_Vehicle_2024'::'Logical Architecture'::'Structure'::'Driver';
                    perform 'eRod_Autonomous_Vehicle_2024 Project'::'eRod_Autonomous_Vehicle_2024'::'Logical Architecture'::'Logical Functions'::'Root Logical Function'.'Report issues' ; 
                    allocation '273e6c1b-f95a-41c3-82b2-366a5bf3b1c1' : ComponentFunctionalAllocation
                        allocate function ::> 'eRod_Autonomous_Vehicle_2024 Project'::'eRod_Autonomous_Vehicle_2024'::'Logical Architecture'::'Logical Functions'::'Root Logical Function'.'Get informed with issues'
                        to component ::> 'eRod_Autonomous_Vehicle_2024 Project'::'eRod_Autonomous_Vehicle_2024'::'Logical Architecture'::'Structure'::'Driver';
                    perform 'eRod_Autonomous_Vehicle_2024 Project'::'eRod_Autonomous_Vehicle_2024'::'Logical Architecture'::'Logical Functions'::'Root Logical Function'.'Get informed with issues' ; 
                    allocation 'b23d822b-d8fd-4e6c-8caf-88b8541438e2' : ComponentFunctionalAllocation
                        allocate function ::> 'eRod_Autonomous_Vehicle_2024 Project'::'eRod_Autonomous_Vehicle_2024'::'Logical Architecture'::'Logical Functions'::'Root Logical Function'.'Get Software-update'
                        to component ::> 'eRod_Autonomous_Vehicle_2024 Project'::'eRod_Autonomous_Vehicle_2024'::'Logical Architecture'::'Structure'::'Driver';
                    perform 'eRod_Autonomous_Vehicle_2024 Project'::'eRod_Autonomous_Vehicle_2024'::'Logical Architecture'::'Logical Functions'::'Root Logical Function'.'Get Software-update' ; 
                    allocation '80cf7544-4f47-4cd3-8574-74f8929780e6' : ComponentFunctionalAllocation
                        allocate function ::> 'eRod_Autonomous_Vehicle_2024 Project'::'eRod_Autonomous_Vehicle_2024'::'Logical Architecture'::'Logical Functions'::'Root Logical Function'.'Obtain car racing experience'
                        to component ::> 'eRod_Autonomous_Vehicle_2024 Project'::'eRod_Autonomous_Vehicle_2024'::'Logical Architecture'::'Structure'::'Driver';
                    perform 'eRod_Autonomous_Vehicle_2024 Project'::'eRod_Autonomous_Vehicle_2024'::'Logical Architecture'::'Logical Functions'::'Root Logical Function'.'Obtain car racing experience' ; 
                    allocation 'bf37e755-3700-4c1c-9cd9-bc989d71bbe1' : ComponentFunctionalAllocation
                        allocate function ::> 'eRod_Autonomous_Vehicle_2024 Project'::'eRod_Autonomous_Vehicle_2024'::'Logical Architecture'::'Logical Functions'::'Root Logical Function'.'Drive vehicle'
                        to component ::> 'eRod_Autonomous_Vehicle_2024 Project'::'eRod_Autonomous_Vehicle_2024'::'Logical Architecture'::'Structure'::'Driver';
                    perform 'eRod_Autonomous_Vehicle_2024 Project'::'eRod_Autonomous_Vehicle_2024'::'Logical Architecture'::'Logical Functions'::'Root Logical Function'.'Drive vehicle' ; 
                    allocation '08c47099-2693-44b0-b3d8-ff2c3235c85c' : ComponentFunctionalAllocation
                        allocate function ::> 'eRod_Autonomous_Vehicle_2024 Project'::'eRod_Autonomous_Vehicle_2024'::'Logical Architecture'::'Logical Functions'::'Root Logical Function'.'Recieve feedback'
                        to component ::> 'eRod_Autonomous_Vehicle_2024 Project'::'eRod_Autonomous_Vehicle_2024'::'Logical Architecture'::'Structure'::'Driver';
                    perform 'eRod_Autonomous_Vehicle_2024 Project'::'eRod_Autonomous_Vehicle_2024'::'Logical Architecture'::'Logical Functions'::'Root Logical Function'.'Recieve feedback' ; 
                    allocation 'd373b6f2-c6b4-4fda-9ff1-493c34f0903d' : ComponentFunctionalAllocation
                        allocate function ::> 'eRod_Autonomous_Vehicle_2024 Project'::'eRod_Autonomous_Vehicle_2024'::'Logical Architecture'::'Logical Functions'::'Root Logical Function'.'Provide solution'
                        to component ::> 'eRod_Autonomous_Vehicle_2024 Project'::'eRod_Autonomous_Vehicle_2024'::'Logical Architecture'::'Structure'::'Driver';
                    perform 'eRod_Autonomous_Vehicle_2024 Project'::'eRod_Autonomous_Vehicle_2024'::'Logical Architecture'::'Logical Functions'::'Root Logical Function'.'Provide solution' ; 
                    port 'CP 1' : ComponentPort { 
                        @CapellaID { eid = "cda6970f-4cf3-4ea0-a296-f640a0d5d00d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                         
                    }  
                    port 'CP 2' : ComponentPort { 
                        @CapellaID { eid = "3c997bbb-1114-49f9-8819-0c8a3457c05c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                         
                    }  
                    ref :>> ownedFunctionalAllocation =  ('eRod_Autonomous_Vehicle_2024 Project'::'eRod_Autonomous_Vehicle_2024'::'Logical Architecture'::'Structure'::'Driver'.'66c977fd-603b-4c73-9075-d7173e0cbb23',
                    'eRod_Autonomous_Vehicle_2024 Project'::'eRod_Autonomous_Vehicle_2024'::'Logical Architecture'::'Structure'::'Driver'.'1bd9afe0-ac5a-4c75-bc0f-c6b8a3fcc88a',
                    'eRod_Autonomous_Vehicle_2024 Project'::'eRod_Autonomous_Vehicle_2024'::'Logical Architecture'::'Structure'::'Driver'.'de99e26b-62cb-4a6e-9fa9-8b10996b826f',
                    'eRod_Autonomous_Vehicle_2024 Project'::'eRod_Autonomous_Vehicle_2024'::'Logical Architecture'::'Structure'::'Driver'.'273e6c1b-f95a-41c3-82b2-366a5bf3b1c1',
                    'eRod_Autonomous_Vehicle_2024 Project'::'eRod_Autonomous_Vehicle_2024'::'Logical Architecture'::'Structure'::'Driver'.'b23d822b-d8fd-4e6c-8caf-88b8541438e2',
                    'eRod_Autonomous_Vehicle_2024 Project'::'eRod_Autonomous_Vehicle_2024'::'Logical Architecture'::'Structure'::'Driver'.'80cf7544-4f47-4cd3-8574-74f8929780e6',
                    'eRod_Autonomous_Vehicle_2024 Project'::'eRod_Autonomous_Vehicle_2024'::'Logical Architecture'::'Structure'::'Driver'.'bf37e755-3700-4c1c-9cd9-bc989d71bbe1',
                    'eRod_Autonomous_Vehicle_2024 Project'::'eRod_Autonomous_Vehicle_2024'::'Logical Architecture'::'Structure'::'Driver'.'08c47099-2693-44b0-b3d8-ff2c3235c85c',
                    'eRod_Autonomous_Vehicle_2024 Project'::'eRod_Autonomous_Vehicle_2024'::'Logical Architecture'::'Structure'::'Driver'.'d373b6f2-c6b4-4fda-9ff1-493c34f0903d'); 
                     
                     
                }  
                part 'Sport-Offroad Buggies' : LogicalComponent { 
                    @CapellaID { eid = "09bdfa6b-f447-4ce7-8e51-b2cd2e19fff5"; } 
                    attribute :>> isAbstract = false; 
                    attribute :>> isActor = true; 
                    attribute :>> isHuman = false; 
                     
                }  
                part 'Environment' : LogicalComponent { 
                    @CapellaID { eid = "5413609c-95b3-4745-901c-eff66faf71ea"; } 
                    attribute :>> isAbstract = false; 
                    attribute :>> isActor = true; 
                    attribute :>> isHuman = false; 
                    port 'CP 1' : ComponentPort { 
                        @CapellaID { eid = "df9d851d-15ed-4c66-b0e2-e4b8882575e5"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                    }  
                    port 'CP 2' : ComponentPort { 
                        @CapellaID { eid = "b72d18ba-7c0a-4e4d-993d-185eddffd258"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                    }  
                    port 'Environment from Motor' : ComponentPort { 
                        @CapellaID { eid = "90729fcf-1f9f-4c2b-be83-e7ea6683b3a6"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                        ref :>> requiredInterfaces =  ('eRod_Autonomous_Vehicle_2024 Project'::'eRod_Autonomous_Vehicle_2024'::'Logical Architecture'::'Interfaces'::'Heat'); 
                    }  
                    part 'Terrain/Roads' : LogicalComponent { 
                        @CapellaID { eid = "9c802b38-231e-4661-ba70-98f389b9c8ad"; } 
                        attribute :>> isAbstract = false; 
                        attribute :>> isActor = true; 
                        attribute :>> isHuman = false; 
                        allocation 'a0f1cd4a-434d-486d-9a03-6f73316f627f' : ComponentFunctionalAllocation
                            allocate function ::> 'eRod_Autonomous_Vehicle_2024 Project'::'eRod_Autonomous_Vehicle_2024'::'Logical Architecture'::'Logical Functions'::'Root Logical Function'.'Provide diverse terrain'
                            to component ::> 'eRod_Autonomous_Vehicle_2024 Project'::'eRod_Autonomous_Vehicle_2024'::'Logical Architecture'::'Structure'::'Environment'.'Terrain/Roads';
                        perform 'eRod_Autonomous_Vehicle_2024 Project'::'eRod_Autonomous_Vehicle_2024'::'Logical Architecture'::'Logical Functions'::'Root Logical Function'.'Provide diverse terrain' ; 
                        allocation 'e1f99225-6739-4e10-a4e2-4518f44671f7' : ComponentFunctionalAllocation
                            allocate function ::> 'eRod_Autonomous_Vehicle_2024 Project'::'eRod_Autonomous_Vehicle_2024'::'Logical Architecture'::'Logical Functions'::'Root Logical Function'.'Provide road markers'
                            to component ::> 'eRod_Autonomous_Vehicle_2024 Project'::'eRod_Autonomous_Vehicle_2024'::'Logical Architecture'::'Structure'::'Environment'.'Terrain/Roads';
                        perform 'eRod_Autonomous_Vehicle_2024 Project'::'eRod_Autonomous_Vehicle_2024'::'Logical Architecture'::'Logical Functions'::'Root Logical Function'.'Provide road markers' ; 
                        allocation 'ad6a41ea-ffba-4dfb-b4c2-a2bd680e54dd' : ComponentFunctionalAllocation
                            allocate function ::> 'eRod_Autonomous_Vehicle_2024 Project'::'eRod_Autonomous_Vehicle_2024'::'Logical Architecture'::'Logical Functions'::'Root Logical Function'.'Resist Front Wheels'
                            to component ::> 'eRod_Autonomous_Vehicle_2024 Project'::'eRod_Autonomous_Vehicle_2024'::'Logical Architecture'::'Structure'::'Environment'.'Terrain/Roads';
                        perform 'eRod_Autonomous_Vehicle_2024 Project'::'eRod_Autonomous_Vehicle_2024'::'Logical Architecture'::'Logical Functions'::'Root Logical Function'.'Resist Front Wheels' ; 
                        ref :>> ownedFunctionalAllocation =  ('eRod_Autonomous_Vehicle_2024 Project'::'eRod_Autonomous_Vehicle_2024'::'Logical Architecture'::'Structure'::'Environment'.'Terrain/Roads'.'a0f1cd4a-434d-486d-9a03-6f73316f627f',
                        'eRod_Autonomous_Vehicle_2024 Project'::'eRod_Autonomous_Vehicle_2024'::'Logical Architecture'::'Structure'::'Environment'.'Terrain/Roads'.'e1f99225-6739-4e10-a4e2-4518f44671f7',
                        'eRod_Autonomous_Vehicle_2024 Project'::'eRod_Autonomous_Vehicle_2024'::'Logical Architecture'::'Structure'::'Environment'.'Terrain/Roads'.'ad6a41ea-ffba-4dfb-b4c2-a2bd680e54dd'); 
                         
                    }  
                    part 'Weather' : LogicalComponent { 
                        @CapellaID { eid = "20f23586-258b-44fa-b138-5a1e75696b61"; } 
                        attribute :>> isAbstract = false; 
                        attribute :>> isActor = true; 
                        attribute :>> isHuman = false; 
                        allocation '3bb63eda-d6ae-4ef0-8af3-858bfddf17cf' : ComponentFunctionalAllocation
                            allocate function ::> 'eRod_Autonomous_Vehicle_2024 Project'::'eRod_Autonomous_Vehicle_2024'::'Logical Architecture'::'Logical Functions'::'Root Logical Function'.'Provide weather'
                            to component ::> 'eRod_Autonomous_Vehicle_2024 Project'::'eRod_Autonomous_Vehicle_2024'::'Logical Architecture'::'Structure'::'Environment'.'Weather';
                        perform 'eRod_Autonomous_Vehicle_2024 Project'::'eRod_Autonomous_Vehicle_2024'::'Logical Architecture'::'Logical Functions'::'Root Logical Function'.'Provide weather' ; 
                        ref :>> ownedFunctionalAllocation =  ('eRod_Autonomous_Vehicle_2024 Project'::'eRod_Autonomous_Vehicle_2024'::'Logical Architecture'::'Structure'::'Environment'.'Weather'.'3bb63eda-d6ae-4ef0-8af3-858bfddf17cf'); 
                         
                    }  
                    part 'External' : LogicalComponent { 
                        @CapellaID { eid = "7fe1e8e3-5174-4aa3-a908-5175d61ceb18"; } 
                        attribute :>> isAbstract = false; 
                        attribute :>> isActor = true; 
                        attribute :>> isHuman = false; 
                        allocation 'da2c7336-4895-43d2-8639-ce0d39763c92' : ComponentFunctionalAllocation
                            allocate function ::> 'eRod_Autonomous_Vehicle_2024 Project'::'eRod_Autonomous_Vehicle_2024'::'Logical Architecture'::'Logical Functions'::'Root Logical Function'.'Reflect light'
                            to component ::> 'eRod_Autonomous_Vehicle_2024 Project'::'eRod_Autonomous_Vehicle_2024'::'Logical Architecture'::'Structure'::'Environment'.'External';
                        perform 'eRod_Autonomous_Vehicle_2024 Project'::'eRod_Autonomous_Vehicle_2024'::'Logical Architecture'::'Logical Functions'::'Root Logical Function'.'Reflect light' ; 
                        ref :>> ownedFunctionalAllocation =  ('eRod_Autonomous_Vehicle_2024 Project'::'eRod_Autonomous_Vehicle_2024'::'Logical Architecture'::'Structure'::'Environment'.'External'.'da2c7336-4895-43d2-8639-ce0d39763c92'); 
                         
                    }  
                    ref :>> ownedLogicalComponents =  ('eRod_Autonomous_Vehicle_2024 Project'::'eRod_Autonomous_Vehicle_2024'::'Logical Architecture'::'Structure'::'Environment'.'Terrain/Roads',
                    'eRod_Autonomous_Vehicle_2024 Project'::'eRod_Autonomous_Vehicle_2024'::'Logical Architecture'::'Structure'::'Environment'.'Weather',
                    'eRod_Autonomous_Vehicle_2024 Project'::'eRod_Autonomous_Vehicle_2024'::'Logical Architecture'::'Structure'::'Environment'.'External'); 
                }  
                part 'Remote Driver' : LogicalComponent { 
                    @CapellaID { eid = "9b9f00e1-c5e8-4607-90ad-5d4e15ef794b"; } 
                    attribute :>> isAbstract = false; 
                    attribute :>> isActor = true; 
                    attribute :>> isHuman = true; 
                    allocation '880d0ef8-a8b1-4f80-b387-d384b2d2cc28' : ComponentFunctionalAllocation
                        allocate function ::> 'eRod_Autonomous_Vehicle_2024 Project'::'eRod_Autonomous_Vehicle_2024'::'Logical Architecture'::'Logical Functions'::'Root Logical Function'.'Vehicle Command'
                        to component ::> 'eRod_Autonomous_Vehicle_2024 Project'::'eRod_Autonomous_Vehicle_2024'::'Logical Architecture'::'Structure'::'Remote Driver';
                    perform 'eRod_Autonomous_Vehicle_2024 Project'::'eRod_Autonomous_Vehicle_2024'::'Logical Architecture'::'Logical Functions'::'Root Logical Function'.'Vehicle Command' ; 
                    allocation '06d412d5-9f84-4395-a6bb-855be925c224' : ComponentFunctionalAllocation
                        allocate function ::> 'eRod_Autonomous_Vehicle_2024 Project'::'eRod_Autonomous_Vehicle_2024'::'Logical Architecture'::'Logical Functions'::'Root Logical Function'.'Receive Status of Progess '
                        to component ::> 'eRod_Autonomous_Vehicle_2024 Project'::'eRod_Autonomous_Vehicle_2024'::'Logical Architecture'::'Structure'::'Remote Driver';
                    perform 'eRod_Autonomous_Vehicle_2024 Project'::'eRod_Autonomous_Vehicle_2024'::'Logical Architecture'::'Logical Functions'::'Root Logical Function'.'Receive Status of Progess ' ; 
                    ref :>> ownedFunctionalAllocation =  ('eRod_Autonomous_Vehicle_2024 Project'::'eRod_Autonomous_Vehicle_2024'::'Logical Architecture'::'Structure'::'Remote Driver'.'880d0ef8-a8b1-4f80-b387-d384b2d2cc28',
                    'eRod_Autonomous_Vehicle_2024 Project'::'eRod_Autonomous_Vehicle_2024'::'Logical Architecture'::'Structure'::'Remote Driver'.'06d412d5-9f84-4395-a6bb-855be925c224'); 
                     
                     
                }  
                interface '925ea2dc-d776-46d0-a7d4-1f7b9b685235' : ComponentExchange 
                    connect source ::> 'eRod_Autonomous_Vehicle_2024 Project'::'eRod_Autonomous_Vehicle_2024'::'Logical Architecture'::'Structure'::'Driver'.'CP 1'
                    to  target ::> 'eRod_Autonomous_Vehicle_2024 Project'::'eRod_Autonomous_Vehicle_2024'::'Logical Architecture'::'Structure'::'eRod System'.'Info' { 
                    @CapellaID { eid = "925ea2dc-d776-46d0-a7d4-1f7b9b685235"; } 
                    attribute :>> kind = ComponentExchangeKind::FLOW; 
                    attribute :>> interfaceName = "Information"; 
                    attribute :>> isOriented = false; 
                }  
                interface '93f54aa2-085f-459b-87ac-38b3ea0d5055' : ComponentExchange 
                    connect source ::> 'eRod_Autonomous_Vehicle_2024 Project'::'eRod_Autonomous_Vehicle_2024'::'Logical Architecture'::'Structure'::'eRod System'.'Exp'
                    to  target ::> 'eRod_Autonomous_Vehicle_2024 Project'::'eRod_Autonomous_Vehicle_2024'::'Logical Architecture'::'Structure'::'Driver'.'CP 2' { 
                    @CapellaID { eid = "93f54aa2-085f-459b-87ac-38b3ea0d5055"; } 
                    attribute :>> kind = ComponentExchangeKind::FLOW; 
                    attribute :>> interfaceName = "Experience"; 
                    attribute :>> isOriented = false; 
                }  
                interface '8f29a472-0fe5-4276-b716-10e79bb5d63a' : ComponentExchange 
                    connect source ::> 'eRod_Autonomous_Vehicle_2024 Project'::'eRod_Autonomous_Vehicle_2024'::'Logical Architecture'::'Structure'::'Environment'.'CP 1'
                    to  target ::> 'eRod_Autonomous_Vehicle_2024 Project'::'eRod_Autonomous_Vehicle_2024'::'Logical Architecture'::'Structure'::'eRod System'.'Sit' { 
                    @CapellaID { eid = "8f29a472-0fe5-4276-b716-10e79bb5d63a"; } 
                    attribute :>> kind = ComponentExchangeKind::FLOW; 
                    attribute :>> interfaceName = "Situations"; 
                    attribute :>> isOriented = false; 
                }  
                interface '550d0246-f686-403f-816d-a8dc7c6cce1a' : ComponentExchange 
                    connect source ::> 'eRod_Autonomous_Vehicle_2024 Project'::'eRod_Autonomous_Vehicle_2024'::'Logical Architecture'::'Structure'::'Environment'.'CP 2'
                    to  target ::> 'eRod_Autonomous_Vehicle_2024 Project'::'eRod_Autonomous_Vehicle_2024'::'Logical Architecture'::'Structure'::'eRod System'.'Temp' { 
                    @CapellaID { eid = "550d0246-f686-403f-816d-a8dc7c6cce1a"; } 
                    attribute :>> kind = ComponentExchangeKind::FLOW; 
                    attribute :>> interfaceName = "Temperature"; 
                    attribute :>> isOriented = false; 
                }  
                interface '06d3f9b3-1592-4a4c-bae8-8a6e9534b811' : ComponentExchange 
                    connect source ::> 'eRod_Autonomous_Vehicle_2024 Project'::'eRod_Autonomous_Vehicle_2024'::'Logical Architecture'::'Structure'::'eRod System'.'Powertrain'.'Electric motor'.'Motor to Environment'
                    to  target ::> 'eRod_Autonomous_Vehicle_2024 Project'::'eRod_Autonomous_Vehicle_2024'::'Logical Architecture'::'Structure'::'Environment'.'Environment from Motor' { 
                    @CapellaID { eid = "06d3f9b3-1592-4a4c-bae8-8a6e9534b811"; } 
                    attribute :>> kind = ComponentExchangeKind::FLOW; 
                    attribute :>> interfaceName = "Heat"; 
                    attribute :>> isOriented = false; 
                    ref :>> convoyedInformations =  ('eRod_Autonomous_Vehicle_2024 Project'::'eRod_Autonomous_Vehicle_2024'::'Logical Architecture'::'Data'::'Heat'); 
                }  
            } 
            package  'Interfaces' {
                @PackageMeta {
                    type = "InterfacePkg";
                } 
                @CapellaID { eid = "4d2f368a-7f4e-41c1-b58e-e3c5547b6295"; } 
                item 'Electricity' : InterfaceItem  { 
                    @CapellaID { eid = "cf80d342-f1e3-4ea5-ae12-6cb86bff5d18"; } 
                    attribute :>> isAbstract = false; 
                    attribute :>> isFinal = false; 
                    attribute :>> isStructural = true; 
                    allocation '77cd7ee0-9304-4896-b38e-7e485d66ab8b' : ExchangeItemAllocation
                        allocate allocatedItem ::> 'eRod_Autonomous_Vehicle_2024 Project'::'eRod_Autonomous_Vehicle_2024'::'Logical Architecture'::'Data'::'Electricity'
                        to allocatingInterface ::> 'eRod_Autonomous_Vehicle_2024 Project'::'eRod_Autonomous_Vehicle_2024'::'Logical Architecture'::'Interfaces'::'Electricity'; 
                    ref :>> ownedExchangeItemAllocations =  ('eRod_Autonomous_Vehicle_2024 Project'::'eRod_Autonomous_Vehicle_2024'::'Logical Architecture'::'Interfaces'::'Electricity'.'77cd7ee0-9304-4896-b38e-7e485d66ab8b'); 
                }  
                item 'Heat' : InterfaceItem  { 
                    @CapellaID { eid = "c3e84c62-a6e5-4028-979b-8f5f823fde7e"; } 
                    attribute :>> isAbstract = false; 
                    attribute :>> isFinal = false; 
                    attribute :>> isStructural = true; 
                    allocation '23495690-edc0-428c-bde2-63b07cddf38e' : ExchangeItemAllocation
                        allocate allocatedItem ::> 'eRod_Autonomous_Vehicle_2024 Project'::'eRod_Autonomous_Vehicle_2024'::'Logical Architecture'::'Data'::'Heat'
                        to allocatingInterface ::> 'eRod_Autonomous_Vehicle_2024 Project'::'eRod_Autonomous_Vehicle_2024'::'Logical Architecture'::'Interfaces'::'Heat'; 
                    ref :>> ownedExchangeItemAllocations =  ('eRod_Autonomous_Vehicle_2024 Project'::'eRod_Autonomous_Vehicle_2024'::'Logical Architecture'::'Interfaces'::'Heat'.'23495690-edc0-428c-bde2-63b07cddf38e'); 
                     
                }  
                item 'Temperature' : InterfaceItem  { 
                    @CapellaID { eid = "55ed94b8-97e0-426f-bee1-6b358d8fbfff"; } 
                    attribute :>> isAbstract = false; 
                    attribute :>> isFinal = false; 
                    attribute :>> isStructural = true; 
                    allocation 'dd127759-dbfb-464f-a3eb-95d366ca9598' : ExchangeItemAllocation
                        allocate allocatedItem ::> 'eRod_Autonomous_Vehicle_2024 Project'::'eRod_Autonomous_Vehicle_2024'::'Logical Architecture'::'Data'::'Temperature'
                        to allocatingInterface ::> 'eRod_Autonomous_Vehicle_2024 Project'::'eRod_Autonomous_Vehicle_2024'::'Logical Architecture'::'Interfaces'::'Temperature'; 
                    ref :>> ownedExchangeItemAllocations =  ('eRod_Autonomous_Vehicle_2024 Project'::'eRod_Autonomous_Vehicle_2024'::'Logical Architecture'::'Interfaces'::'Temperature'.'dd127759-dbfb-464f-a3eb-95d366ca9598'); 
                }  
            } 
            package  'Data' {
                @PackageMeta {
                    type = "DataPkg";
                } 
                @CapellaID { eid = "3eb028d3-bcee-4db6-8710-0b594c1d4c1f"; } 
                item 'Electricity' : ExchangeItem  { 
                    @CapellaID { eid = "c88ea953-84b6-4168-8a85-bbad7cf0aca1"; } 
                    attribute :>> isAbstract = false; 
                    attribute :>> exchangeMechanism = ExchangeMechanism::FLOW; 
                    attribute :>> isFinal = false; 
                    item 'Electricity' : ExchangeItemElement { 
                        @CapellaID { eid = "571fc31a-301f-4ab3-b0ad-85569a3daf3b"; } 
                        attribute :>> isComposite = true; 
                        attribute :>> direction = ParameterDirection::UNSET; 
                        attribute :>> kind = ElementKind::TYPE; 
                        attribute :>> isMaxInclusive = false; 
                        attribute :>> isMinInclusive = false; 
                        attribute :>> isOrdered = false; 
                        attribute :>> isUnique = false; 
                         
                         
                    } 
                    ref :>> ownedElements =  ('eRod_Autonomous_Vehicle_2024 Project'::'eRod_Autonomous_Vehicle_2024'::'Logical Architecture'::'Data'::'Electricity'.'Electricity'); 
                }  
                item 'Heat' : ExchangeItem  { 
                    @CapellaID { eid = "67b6fa8c-4de2-4f71-8a29-b4c95e431b35"; } 
                    attribute :>> isAbstract = false; 
                    attribute :>> exchangeMechanism = ExchangeMechanism::FLOW; 
                    attribute :>> isFinal = false; 
                    item 'ExchangeItemElement 2' : ExchangeItemElement { 
                        @CapellaID { eid = "af4ca98a-06d0-4c5e-aafc-29bb56ec86dc"; } 
                        attribute :>> isComposite = true; 
                        attribute :>> direction = ParameterDirection::UNSET; 
                        attribute :>> kind = ElementKind::TYPE; 
                        attribute :>> isMaxInclusive = false; 
                        attribute :>> isMinInclusive = false; 
                        attribute :>> isOrdered = false; 
                        attribute :>> isUnique = false; 
                         
                         
                        ref :>> abstractType = 'eRod_Autonomous_Vehicle_2024 Project'::'eRod_Autonomous_Vehicle_2024'::'Logical Architecture'::'Data'::'Rotor';
                    } 
                    item 'ExchangeItemElement 3' : ExchangeItemElement { 
                        @CapellaID { eid = "9fd5f63f-4215-4e7f-8351-020101cfd222"; } 
                        attribute :>> isComposite = true; 
                        attribute :>> direction = ParameterDirection::UNSET; 
                        attribute :>> kind = ElementKind::TYPE; 
                        attribute :>> isMaxInclusive = false; 
                        attribute :>> isMinInclusive = false; 
                        attribute :>> isOrdered = false; 
                        attribute :>> isUnique = false; 
                         
                         
                        ref :>> abstractType = 'eRod_Autonomous_Vehicle_2024 Project'::'eRod_Autonomous_Vehicle_2024'::'Logical Architecture'::'Data'::'Stator';
                    } 
                    item 'ExchangeItemElement 4' : ExchangeItemElement { 
                        @CapellaID { eid = "bf7364bc-df17-4a6b-b216-0082ad886bdd"; } 
                        attribute :>> isComposite = true; 
                        attribute :>> direction = ParameterDirection::UNSET; 
                        attribute :>> kind = ElementKind::TYPE; 
                        attribute :>> isMaxInclusive = false; 
                        attribute :>> isMinInclusive = false; 
                        attribute :>> isOrdered = false; 
                        attribute :>> isUnique = false; 
                         
                         
                        ref :>> abstractType = 'eRod_Autonomous_Vehicle_2024 Project'::'eRod_Autonomous_Vehicle_2024'::'Logical Architecture'::'Data'::'Housing';
                    } 
                     
                    ref :>> ownedElements =  ('eRod_Autonomous_Vehicle_2024 Project'::'eRod_Autonomous_Vehicle_2024'::'Logical Architecture'::'Data'::'Heat'.'ExchangeItemElement 2',
                    'eRod_Autonomous_Vehicle_2024 Project'::'eRod_Autonomous_Vehicle_2024'::'Logical Architecture'::'Data'::'Heat'.'ExchangeItemElement 3',
                    'eRod_Autonomous_Vehicle_2024 Project'::'eRod_Autonomous_Vehicle_2024'::'Logical Architecture'::'Data'::'Heat'.'ExchangeItemElement 4'); 
                }  
                item 'Temperature' : ExchangeItem  { 
                    @CapellaID { eid = "3fb7dadb-e92c-42e6-8022-2b7a5ebf142b"; } 
                    attribute :>> isAbstract = false; 
                    attribute :>> exchangeMechanism = ExchangeMechanism::SHARED_DATA; 
                    attribute :>> isFinal = false; 
                    item 'Temperature' : ExchangeItemElement { 
                        @CapellaID { eid = "41f3077e-c26c-45be-8921-178acec7cde5"; } 
                        attribute :>> isComposite = true; 
                        attribute :>> direction = ParameterDirection::UNSET; 
                        attribute :>> kind = ElementKind::TYPE; 
                        attribute :>> isMaxInclusive = false; 
                        attribute :>> isMinInclusive = false; 
                        attribute :>> isOrdered = false; 
                        attribute :>> isUnique = false; 
                         
                         
                    } 
                    ref :>> ownedElements =  ('eRod_Autonomous_Vehicle_2024 Project'::'eRod_Autonomous_Vehicle_2024'::'Logical Architecture'::'Data'::'Temperature'.'Temperature'); 
                }  
                package  'SI Units' {
                    @PackageMeta {
                        type = "DataPkg";
                    } 
                    @CapellaID { eid = "fe5f48ad-ff09-4541-b281-0c67438c5628"; } 
                    attribute <'second'> 'second' : ARCADIAUnit; 
                    attribute <'metre'> 'metre' : ARCADIAUnit; 
                    attribute <'Degree Celsius'> 'Degree Celsius' : ARCADIAUnit; 
                    attribute <'Ampere'> 'Ampere' : ARCADIAUnit; 
                    attribute <'Kilogram'> 'Kilogram' : ARCADIAUnit; 
                    attribute <'Volt'> 'Volt' : ARCADIAUnit; 
                    attribute <'Watt'> 'Watt' : ARCADIAUnit; 
                    attribute <'W/m**2/degC'> 'W/m**2/degC' : ARCADIAUnit; 
                    attribute <'Nm'> 'Nm' : ARCADIAUnit; 
                    attribute <'m/s'> 'm/s' : ARCADIAUnit; 
                    attribute <'N'> 'N' : ARCADIAUnit; 
                    attribute <'Newton'> 'Newton' : ARCADIAUnit; 
                    attribute <'Degree (Angle)'> 'Degree (Angle)' : ARCADIAUnit; 
                } 
                package  'Parameter' {
                    @PackageMeta {
                        type = "DataPkg";
                    } 
                    @CapellaID { eid = "0b83f2ad-9d15-42a4-9b9a-79e025ac8815"; } 
                } 
                item 'Motor' : Class { 
                    @CapellaID { eid = "1c49ee99-d5d5-41d2-b78e-d1b38862e449"; } 
                    attribute :>> isAbstract = false; 
                    attribute :>> isFinal = false; 
                    attribute :>> isPrimitive = false; 
                }  
                item 'Rotor' : Class { 
                    @CapellaID { eid = "6f13e4ba-3ecc-4107-91bc-3678451fc7f6"; } 
                    attribute :>> isAbstract = false; 
                    attribute :>> isFinal = false; 
                    attribute :>> isPrimitive = false; 
                }  
                item 'Stator' : Class { 
                    @CapellaID { eid = "65a0dcac-ce09-478e-a63a-65602152e103"; } 
                    attribute :>> isAbstract = false; 
                    attribute :>> isFinal = false; 
                    attribute :>> isPrimitive = false; 
                }  
                item 'Housing' : Class { 
                    @CapellaID { eid = "f4688f2c-a2ea-43b2-a922-2d11c9d31c23"; } 
                    attribute :>> isAbstract = false; 
                    attribute :>> isFinal = false; 
                    attribute :>> isPrimitive = false; 
                }  
            } 
            package  'Capabilities' {
                @PackageMeta {
                    type = "CapabilityRealizationPkg";
                } 
                @CapellaID { eid = "f70ebc0c-0dd9-4712-8621-bf39f0be6245"; } 
                use case 'Software Update' : CapabilityRealization { 
                    @CapellaID { eid = "d9a21755-e318-43ae-9a89-1d72f8d189e1"; } 
                    actor 'Vehicle Control Module' = 'eRod_Autonomous_Vehicle_2024 Project'::'eRod_Autonomous_Vehicle_2024'::'Logical Architecture'::'Structure'::'eRod System'.'Vehicle Control Module'; 
                    actor 'Temperature controll unit' = 'eRod_Autonomous_Vehicle_2024 Project'::'eRod_Autonomous_Vehicle_2024'::'Logical Architecture'::'Structure'::'eRod System'.'Powertrain'.'ECU'.'Temperature controll unit'; 
                    actor 'Power controll unit' = 'eRod_Autonomous_Vehicle_2024 Project'::'eRod_Autonomous_Vehicle_2024'::'Logical Architecture'::'Structure'::'eRod System'.'Powertrain'.'ECU'.'Power controll unit'; 
                    actor 'Rotor' = 'eRod_Autonomous_Vehicle_2024 Project'::'eRod_Autonomous_Vehicle_2024'::'Logical Architecture'::'Structure'::'eRod System'.'Powertrain'.'Electric motor'.'Rotor'; 
                    actor 'Stator' = 'eRod_Autonomous_Vehicle_2024 Project'::'eRod_Autonomous_Vehicle_2024'::'Logical Architecture'::'Structure'::'eRod System'.'Powertrain'.'Stator'; 
                    actor 'Housing' = 'eRod_Autonomous_Vehicle_2024 Project'::'eRod_Autonomous_Vehicle_2024'::'Logical Architecture'::'Structure'::'eRod System'.'Powertrain'.'Electric motor'.'Housing'; 
                    actor 'Electric motor' = 'eRod_Autonomous_Vehicle_2024 Project'::'eRod_Autonomous_Vehicle_2024'::'Logical Architecture'::'Structure'::'eRod System'.'Powertrain'.'Electric motor'; 
                    actor 'Driver' = 'eRod_Autonomous_Vehicle_2024 Project'::'eRod_Autonomous_Vehicle_2024'::'Logical Architecture'::'Structure'::'Driver'; 
                    actor 'eRod System' = 'eRod_Autonomous_Vehicle_2024 Project'::'eRod_Autonomous_Vehicle_2024'::'Logical Architecture'::'Structure'::'eRod System'; 
                    actor 'ECU' = 'eRod_Autonomous_Vehicle_2024 Project'::'eRod_Autonomous_Vehicle_2024'::'Logical Architecture'::'Structure'::'eRod System'.'Powertrain'.'ECU'; 
                    actor 'Powertrain' = 'eRod_Autonomous_Vehicle_2024 Project'::'eRod_Autonomous_Vehicle_2024'::'Logical Architecture'::'Structure'::'eRod System'.'Powertrain'; 
                     
                     
                }  
                use case 'Sporty drive' : CapabilityRealization { 
                    @CapellaID { eid = "34e106a6-d804-40c6-adb8-110ecb409174"; } 
                    ref action 'd14a06fa-2bba-402f-b533-d9d11697435c' = 'eRod_Autonomous_Vehicle_2024 Project'::'eRod_Autonomous_Vehicle_2024'::'Logical Architecture'::'Logical Functions'::'Root Logical Function'.'Vehicle Steering'; 
                     
                     
                }  
                use case 'Improve performance' : CapabilityRealization { 
                    @CapellaID { eid = "2855d643-8dd5-486d-b2db-244fe38b9b93"; } 
                    ref action 'bb306386-9984-4bb8-a6cb-40fad3d6329f' = 'eRod_Autonomous_Vehicle_2024 Project'::'eRod_Autonomous_Vehicle_2024'::'Logical Architecture'::'Logical Functions'::'Root Logical Function'.'Drive on Track'; 
                    ref action 'c23281ef-e8fc-435c-a900-72b95e6cb2fb' = 'eRod_Autonomous_Vehicle_2024 Project'::'eRod_Autonomous_Vehicle_2024'::'Logical Architecture'::'Logical Functions'::'Root Logical Function'.'Detect Temp Issues'; 
                     
                }  
                use case 'Finish race track' : CapabilityRealization { 
                    @CapellaID { eid = "7dfa6e41-d2ad-4d2c-a9de-bfa96b177e11"; } 
                     
                }  
                use case 'Quick solution for the issues' : CapabilityRealization { 
                    @CapellaID { eid = "769516ea-54ba-465e-b5a1-b813ade49f60"; } 
                     
                }  
                use case 'Autonmous Driving' : CapabilityRealization { 
                    @CapellaID { eid = "b0b09af4-b5e9-4d07-b345-1ca56ec5a2f6"; } 
                    ref action '802b8b2a-db91-4fcf-97ea-460d43046692' = 'eRod_Autonomous_Vehicle_2024 Project'::'eRod_Autonomous_Vehicle_2024'::'Logical Architecture'::'Logical Functions'::'Root Logical Function'.'Lane Keep Assist (LKA)'; 
                     
                     
                }  
                use case 'Lane Keeping Assistant (LKA)' : CapabilityRealization { 
                    @CapellaID { eid = "fb0f35ba-d494-4d26-be7c-1c2dd2213cd1"; } 
                    ref action '9a6be45d-15ec-4509-8387-ca6685e60b2c' = 'eRod_Autonomous_Vehicle_2024 Project'::'eRod_Autonomous_Vehicle_2024'::'Logical Architecture'::'Logical Functions'::'Root Logical Function'.'Lane Keep Assist (LKA)'; 
                     
                     
                }  
                use case 'Forward Collision Warning (FCW)' : CapabilityRealization { 
                    @CapellaID { eid = "5b61b17b-a7b5-4335-b4ef-4068dffce598"; } 
                    ref action 'eded5dbb-32c6-4eed-8664-e75e7869079f' = 'eRod_Autonomous_Vehicle_2024 Project'::'eRod_Autonomous_Vehicle_2024'::'Logical Architecture'::'Logical Functions'::'Root Logical Function'.'Forward Collision Warning (FCW)'; 
                     
                     
                }  
                use case 'Adaptive Cruise Control (ACC)' : CapabilityRealization { 
                    @CapellaID { eid = "219134e1-c1a2-496d-9801-11d22b262f48"; } 
                    ref action 'f5fe40de-83fb-4326-b36b-054461c65b3f' = 'eRod_Autonomous_Vehicle_2024 Project'::'eRod_Autonomous_Vehicle_2024'::'Logical Architecture'::'Logical Functions'::'Root Logical Function'.'Adaptive Cruise Control (ACC)'; 
                     
                     
                }  
                use case 'Autonomous Emergency Braking (AEB)' : CapabilityRealization { 
                    @CapellaID { eid = "a3ceeeee-c8e1-465f-9d2a-cb19faba3791"; } 
                    ref action '1acaf0ea-ca01-4ab7-bacd-49de0ab909da' = 'eRod_Autonomous_Vehicle_2024 Project'::'eRod_Autonomous_Vehicle_2024'::'Logical Architecture'::'Logical Functions'::'Root Logical Function'.'Adaptive Cruise Control (ACC)'; 
                     
                     
                }  
            } 
        } 
        package  'Physical Architecture' {
            @PackageMeta {
                type = "PhysicalArchitecture";
            } 
            @CapellaID { eid = "be3dd5a0-1575-4cb4-a583-f6741b7b1360"; } 
            package  'Physical Functions' {
                @PackageMeta {
                    type = "PhysicalFunctionPkg";
                } 
                @CapellaID { eid = "8f8cd3b1-1039-4376-9b5f-d0326ce69624"; } 
                action 'Root Physical Function' : PhysicalFunction  { 
                    @CapellaID { eid = "db610e2f-ff17-40c6-bf47-1e52b591b585"; } 
                    attribute :>> aggregationKind = AggregationKind::UNSET; 
                    attribute :>> isFinal = false; 
                    attribute :>> isAbstract = false; 
                    attribute :>> isDerived = false; 
                    attribute :>> isPartOfKey = false; 
                    attribute :>> isReadOnly = false; 
                    attribute :>> isStatic = false; 
                    attribute :>> kind = FunctionKind::FUNCTION; 
                    attribute :>> isMaxInclusive = false; 
                    attribute :>> isMinInclusive = false; 
                    attribute :>> isOrdered = false; 
                    attribute :>> isUnique = false; 
                    action 'Overheating' : FunctionalChain  { 
                        @CapellaID { eid = "ff51d936-09de-464e-b781-fcc72b0a38bf"; } 
                        attribute :>> kind = FunctionalChainKind::SIMPLE; 
                        ref action '0702bf63-0c84-4abb-b617-d9a7d8893349' = 'eRod_Autonomous_Vehicle_2024 Project'::'eRod_Autonomous_Vehicle_2024'::'Physical Architecture'::'Physical Functions'::'Root Physical Function'.'Drive on a race track'; 
                        connection 'c0704af5-2e27-4577-92f6-599bbf4a880a' : FunctionalChainInvolvementLink 
                            connect source ::> 'eRod_Autonomous_Vehicle_2024 Project'::'eRod_Autonomous_Vehicle_2024'::'Physical Architecture'::'Physical Functions'::'Root Physical Function'.'Overheating'.'0702bf63-0c84-4abb-b617-d9a7d8893349'
                            to  target ::> 'eRod_Autonomous_Vehicle_2024 Project'::'eRod_Autonomous_Vehicle_2024'::'Physical Architecture'::'Physical Functions'::'Root Physical Function'.'Overheating'.'78ebf61e-e32d-421f-b86d-dee3196c7bbb' {

                                ref :>> involved = 'eRod_Autonomous_Vehicle_2024 Project'::'eRod_Autonomous_Vehicle_2024'::'Physical Architecture'::'Physical Functions'::'Root Physical Function'.'3e32e08c-4ec4-4d11-984b-e71b9f8a7eba';

                            } 
                        ref action '78ebf61e-e32d-421f-b86d-dee3196c7bbb' = 'eRod_Autonomous_Vehicle_2024 Project'::'eRod_Autonomous_Vehicle_2024'::'Physical Architecture'::'Physical Functions'::'Root Physical Function'.'Motor Start'; 
                        connection 'df96966f-d285-4ad7-9157-6b5317628381' : FunctionalChainInvolvementLink 
                            connect source ::> 'eRod_Autonomous_Vehicle_2024 Project'::'eRod_Autonomous_Vehicle_2024'::'Physical Architecture'::'Physical Functions'::'Root Physical Function'.'Overheating'.'78ebf61e-e32d-421f-b86d-dee3196c7bbb'
                            to  target ::> 'eRod_Autonomous_Vehicle_2024 Project'::'eRod_Autonomous_Vehicle_2024'::'Physical Architecture'::'Physical Functions'::'Root Physical Function'.'Overheating'.'f14d6155-81cb-4fb1-b4be-7f91dba8d31d' {

                                ref :>> involved = 'eRod_Autonomous_Vehicle_2024 Project'::'eRod_Autonomous_Vehicle_2024'::'Physical Architecture'::'Physical Functions'::'Root Physical Function'.'456055aa-4b85-43b2-8567-70e2f0fad6bf';

                            } 
                        ref action 'f14d6155-81cb-4fb1-b4be-7f91dba8d31d' = 'eRod_Autonomous_Vehicle_2024 Project'::'eRod_Autonomous_Vehicle_2024'::'Physical Architecture'::'Physical Functions'::'Root Physical Function'.'Transfer Energy'.'Acquire electrical Energy'; 
                        connection 'b838ed1c-4740-4c42-a6cd-66f41cf89322' : FunctionalChainInvolvementLink 
                            connect source ::> 'eRod_Autonomous_Vehicle_2024 Project'::'eRod_Autonomous_Vehicle_2024'::'Physical Architecture'::'Physical Functions'::'Root Physical Function'.'Overheating'.'f14d6155-81cb-4fb1-b4be-7f91dba8d31d'
                            to  target ::> 'eRod_Autonomous_Vehicle_2024 Project'::'eRod_Autonomous_Vehicle_2024'::'Physical Architecture'::'Physical Functions'::'Root Physical Function'.'Overheating'.'18ae9c00-01c4-43b2-ace3-aac773a645a2' {

                                ref :>> involved = 'eRod_Autonomous_Vehicle_2024 Project'::'eRod_Autonomous_Vehicle_2024'::'Physical Architecture'::'Physical Functions'::'Root Physical Function'.'3456a6a1-0825-47fd-bafc-064d5940fc0c';

                            } 
                        ref action '18ae9c00-01c4-43b2-ace3-aac773a645a2' = 'eRod_Autonomous_Vehicle_2024 Project'::'eRod_Autonomous_Vehicle_2024'::'Physical Architecture'::'Physical Functions'::'Root Physical Function'.'deliver mechanical power'; 
                        ref action '77b96546-be5c-4cae-8252-38a46d112bc9' = 'eRod_Autonomous_Vehicle_2024 Project'::'eRod_Autonomous_Vehicle_2024'::'Physical Architecture'::'Physical Functions'::'Root Physical Function'.'Generate heat (Rotor)'; 
                        connection '083c3265-09c3-4794-9c13-045a4e2d0a88' : FunctionalChainInvolvementLink 
                            connect source ::> 'eRod_Autonomous_Vehicle_2024 Project'::'eRod_Autonomous_Vehicle_2024'::'Physical Architecture'::'Physical Functions'::'Root Physical Function'.'Overheating'.'18ae9c00-01c4-43b2-ace3-aac773a645a2'
                            to  target ::> 'eRod_Autonomous_Vehicle_2024 Project'::'eRod_Autonomous_Vehicle_2024'::'Physical Architecture'::'Physical Functions'::'Root Physical Function'.'Overheating'.'77b96546-be5c-4cae-8252-38a46d112bc9' {

                                ref :>> involved = 'eRod_Autonomous_Vehicle_2024 Project'::'eRod_Autonomous_Vehicle_2024'::'Physical Architecture'::'Physical Functions'::'Root Physical Function'.'bf906ee8-dedd-4fe1-91d5-f7853ff901ae';

                            } 
                        connection '5fc281a4-f4fa-4fec-bc0b-d8903f499bbf' : FunctionalChainInvolvementLink 
                            connect source ::> 'eRod_Autonomous_Vehicle_2024 Project'::'eRod_Autonomous_Vehicle_2024'::'Physical Architecture'::'Physical Functions'::'Root Physical Function'.'Overheating'.'77b96546-be5c-4cae-8252-38a46d112bc9'
                            to  target ::> 'eRod_Autonomous_Vehicle_2024 Project'::'eRod_Autonomous_Vehicle_2024'::'Physical Architecture'::'Physical Functions'::'Root Physical Function'.'Overheating'.'dbbb9d5c-6697-4db6-a072-7702282ceb51' {

                                ref :>> involved = 'eRod_Autonomous_Vehicle_2024 Project'::'eRod_Autonomous_Vehicle_2024'::'Physical Architecture'::'Physical Functions'::'Root Physical Function'.'25a019eb-1f3e-4af4-910c-1c9ec88d3bbd';

                            } 
                        ref action 'dbbb9d5c-6697-4db6-a072-7702282ceb51' = 'eRod_Autonomous_Vehicle_2024 Project'::'eRod_Autonomous_Vehicle_2024'::'Physical Architecture'::'Physical Functions'::'Root Physical Function'.'Gather 21'; 
                        connection 'af89c7b5-2761-4d77-9745-4ec0e8354181' : FunctionalChainInvolvementLink 
                            connect source ::> 'eRod_Autonomous_Vehicle_2024 Project'::'eRod_Autonomous_Vehicle_2024'::'Physical Architecture'::'Physical Functions'::'Root Physical Function'.'Overheating'.'f14d6155-81cb-4fb1-b4be-7f91dba8d31d'
                            to  target ::> 'eRod_Autonomous_Vehicle_2024 Project'::'eRod_Autonomous_Vehicle_2024'::'Physical Architecture'::'Physical Functions'::'Root Physical Function'.'Overheating'.'533d6e41-8fcf-4ff7-a7b9-09a575308790' {

                                ref :>> involved = 'eRod_Autonomous_Vehicle_2024 Project'::'eRod_Autonomous_Vehicle_2024'::'Physical Architecture'::'Physical Functions'::'Root Physical Function'.'263913cb-fa3b-4d7a-8f60-9cb9c8fb507a';

                            } 
                        ref action '533d6e41-8fcf-4ff7-a7b9-09a575308790' = 'eRod_Autonomous_Vehicle_2024 Project'::'eRod_Autonomous_Vehicle_2024'::'Physical Architecture'::'Physical Functions'::'Root Physical Function'.'Provide magnetic field'; 
                        connection '416cc4f9-baaa-4784-a037-30543da2908d' : FunctionalChainInvolvementLink 
                            connect source ::> 'eRod_Autonomous_Vehicle_2024 Project'::'eRod_Autonomous_Vehicle_2024'::'Physical Architecture'::'Physical Functions'::'Root Physical Function'.'Overheating'.'eaf2eb09-31b0-437f-85ff-187ca1f2b3ac'
                            to  target ::> 'eRod_Autonomous_Vehicle_2024 Project'::'eRod_Autonomous_Vehicle_2024'::'Physical Architecture'::'Physical Functions'::'Root Physical Function'.'Overheating'.'dbbb9d5c-6697-4db6-a072-7702282ceb51' {

                                ref :>> involved = 'eRod_Autonomous_Vehicle_2024 Project'::'eRod_Autonomous_Vehicle_2024'::'Physical Architecture'::'Physical Functions'::'Root Physical Function'.'56b5a67c-b469-4ef5-af7d-e1fb7e3bfcf5';

                            } 
                        ref action 'eaf2eb09-31b0-437f-85ff-187ca1f2b3ac' = 'eRod_Autonomous_Vehicle_2024 Project'::'eRod_Autonomous_Vehicle_2024'::'Physical Architecture'::'Physical Functions'::'Root Physical Function'.'Generate Heat (Stator)'; 
                        connection 'ef6c5fb9-ae45-4f5c-9ac8-a7cf89d42238' : FunctionalChainInvolvementLink 
                            connect source ::> 'eRod_Autonomous_Vehicle_2024 Project'::'eRod_Autonomous_Vehicle_2024'::'Physical Architecture'::'Physical Functions'::'Root Physical Function'.'Overheating'.'dbbb9d5c-6697-4db6-a072-7702282ceb51'
                            to  target ::> 'eRod_Autonomous_Vehicle_2024 Project'::'eRod_Autonomous_Vehicle_2024'::'Physical Architecture'::'Physical Functions'::'Root Physical Function'.'Overheating'.'9f90b2e7-98ac-4edd-9fd7-e4da7fa88aa6' {

                                ref :>> involved = 'eRod_Autonomous_Vehicle_2024 Project'::'eRod_Autonomous_Vehicle_2024'::'Physical Architecture'::'Physical Functions'::'Root Physical Function'.'58863c2d-ded0-49c9-8337-1aaeec5c9015';

                            } 
                        ref action '9f90b2e7-98ac-4edd-9fd7-e4da7fa88aa6' = 'eRod_Autonomous_Vehicle_2024 Project'::'eRod_Autonomous_Vehicle_2024'::'Physical Architecture'::'Physical Functions'::'Root Physical Function'.'Transfer heat'; 
                        connection '5b4712a7-4ece-4b81-b09f-65716628b56b' : FunctionalChainInvolvementLink 
                            connect source ::> 'eRod_Autonomous_Vehicle_2024 Project'::'eRod_Autonomous_Vehicle_2024'::'Physical Architecture'::'Physical Functions'::'Root Physical Function'.'Overheating'.'9f90b2e7-98ac-4edd-9fd7-e4da7fa88aa6'
                            to  target ::> 'eRod_Autonomous_Vehicle_2024 Project'::'eRod_Autonomous_Vehicle_2024'::'Physical Architecture'::'Physical Functions'::'Root Physical Function'.'Overheating'.'0f11f47e-fea2-4ceb-8f88-d865bf0fa492' {

                                ref :>> involved = 'eRod_Autonomous_Vehicle_2024 Project'::'eRod_Autonomous_Vehicle_2024'::'Physical Architecture'::'Physical Functions'::'Root Physical Function'.'7ae44802-8c02-4afc-9143-cd74794cb224';

                            } 
                        ref action '0f11f47e-fea2-4ceb-8f88-d865bf0fa492' = 'eRod_Autonomous_Vehicle_2024 Project'::'eRod_Autonomous_Vehicle_2024'::'Physical Architecture'::'Physical Functions'::'Root Physical Function'.'Motor protect'.'Monitor temperature'; 
                        connection '5a90380d-1559-4c44-8310-10d83d95850f' : FunctionalChainInvolvementLink 
                            connect source ::> 'eRod_Autonomous_Vehicle_2024 Project'::'eRod_Autonomous_Vehicle_2024'::'Physical Architecture'::'Physical Functions'::'Root Physical Function'.'Overheating'.'0f11f47e-fea2-4ceb-8f88-d865bf0fa492'
                            to  target ::> 'eRod_Autonomous_Vehicle_2024 Project'::'eRod_Autonomous_Vehicle_2024'::'Physical Architecture'::'Physical Functions'::'Root Physical Function'.'Overheating'.'d3c0f00d-b765-45c7-b5db-c96e4a9b2b2f' {

                                ref :>> involved = 'eRod_Autonomous_Vehicle_2024 Project'::'eRod_Autonomous_Vehicle_2024'::'Physical Architecture'::'Physical Functions'::'Root Physical Function'.'Motor protect'.'c4dd0ad9-1a8c-47e6-952c-e6c0eed9c14f';

                            } 
                        ref action 'd3c0f00d-b765-45c7-b5db-c96e4a9b2b2f' = 'eRod_Autonomous_Vehicle_2024 Project'::'eRod_Autonomous_Vehicle_2024'::'Physical Architecture'::'Physical Functions'::'Root Physical Function'.'Motor protect'.'Detect temperature limit'; 
                        connection '37040447-0cf9-45c9-a800-534e98f5f266' : FunctionalChainInvolvementLink 
                            connect source ::> 'eRod_Autonomous_Vehicle_2024 Project'::'eRod_Autonomous_Vehicle_2024'::'Physical Architecture'::'Physical Functions'::'Root Physical Function'.'Overheating'.'d3c0f00d-b765-45c7-b5db-c96e4a9b2b2f'
                            to  target ::> 'eRod_Autonomous_Vehicle_2024 Project'::'eRod_Autonomous_Vehicle_2024'::'Physical Architecture'::'Physical Functions'::'Root Physical Function'.'Overheating'.'d085ff76-fdd6-4202-8281-9e1af86fd2a3' {

                                ref :>> involved = 'eRod_Autonomous_Vehicle_2024 Project'::'eRod_Autonomous_Vehicle_2024'::'Physical Architecture'::'Physical Functions'::'Root Physical Function'.'3323da4e-ac6a-472c-8e08-4f552dc0e710';

                            } 
                        ref action 'd085ff76-fdd6-4202-8281-9e1af86fd2a3' = 'eRod_Autonomous_Vehicle_2024 Project'::'eRod_Autonomous_Vehicle_2024'::'Physical Architecture'::'Physical Functions'::'Root Physical Function'.'Motor overheating warning '; 
                         
                    }  
                    action 'Car racing absorbed' : FunctionalChain  { 
                        @CapellaID { eid = "f708d38e-df62-4c17-910d-8f242276dcaf"; } 
                        attribute :>> kind = FunctionalChainKind::SIMPLE; 
                        ref action '442e4aae-fca7-4070-a739-701525839c22' = 'eRod_Autonomous_Vehicle_2024 Project'::'eRod_Autonomous_Vehicle_2024'::'Physical Architecture'::'Physical Functions'::'Root Physical Function'.'Motor protect'.'Detect temperature limit'; 
                        connection 'b3b4b343-4e8e-4878-984d-218b304cbf0d' : FunctionalChainInvolvementLink 
                            connect source ::> 'eRod_Autonomous_Vehicle_2024 Project'::'eRod_Autonomous_Vehicle_2024'::'Physical Architecture'::'Physical Functions'::'Root Physical Function'.'Car racing absorbed'.'442e4aae-fca7-4070-a739-701525839c22'
                            to  target ::> 'eRod_Autonomous_Vehicle_2024 Project'::'eRod_Autonomous_Vehicle_2024'::'Physical Architecture'::'Physical Functions'::'Root Physical Function'.'Car racing absorbed'.'a75967be-b607-49db-9a04-76eecbfc82a3' {

                                ref :>> involved = 'eRod_Autonomous_Vehicle_2024 Project'::'eRod_Autonomous_Vehicle_2024'::'Physical Architecture'::'Physical Functions'::'Root Physical Function'.'Motor protect'.'db9bf532-3311-4399-a389-6176776af754';

                            } 
                        ref action 'a75967be-b607-49db-9a04-76eecbfc82a3' = 'eRod_Autonomous_Vehicle_2024 Project'::'eRod_Autonomous_Vehicle_2024'::'Physical Architecture'::'Physical Functions'::'Root Physical Function'.'Motor protect'.'Reduce power'; 
                        connection '163d4d87-2d81-49e7-b766-ec557c4d455e' : FunctionalChainInvolvementLink 
                            connect source ::> 'eRod_Autonomous_Vehicle_2024 Project'::'eRod_Autonomous_Vehicle_2024'::'Physical Architecture'::'Physical Functions'::'Root Physical Function'.'Car racing absorbed'.'a75967be-b607-49db-9a04-76eecbfc82a3'
                            to  target ::> 'eRod_Autonomous_Vehicle_2024 Project'::'eRod_Autonomous_Vehicle_2024'::'Physical Architecture'::'Physical Functions'::'Root Physical Function'.'Car racing absorbed'.'b6c115f3-0723-4f5a-8e8b-b6da5bba839c' {

                                ref :>> involved = 'eRod_Autonomous_Vehicle_2024 Project'::'eRod_Autonomous_Vehicle_2024'::'Physical Architecture'::'Physical Functions'::'Root Physical Function'.'e3f1fb22-0869-4f7a-af75-8be9de9dc08b';

                            } 
                        ref action 'b6c115f3-0723-4f5a-8e8b-b6da5bba839c' = 'eRod_Autonomous_Vehicle_2024 Project'::'eRod_Autonomous_Vehicle_2024'::'Physical Architecture'::'Physical Functions'::'Root Physical Function'.'deliver mechanical power'; 
                        connection '4e3c3a55-21da-4fe9-ab58-9c8a657f34bc' : FunctionalChainInvolvementLink 
                            connect source ::> 'eRod_Autonomous_Vehicle_2024 Project'::'eRod_Autonomous_Vehicle_2024'::'Physical Architecture'::'Physical Functions'::'Root Physical Function'.'Car racing absorbed'.'b6c115f3-0723-4f5a-8e8b-b6da5bba839c'
                            to  target ::> 'eRod_Autonomous_Vehicle_2024 Project'::'eRod_Autonomous_Vehicle_2024'::'Physical Architecture'::'Physical Functions'::'Root Physical Function'.'Car racing absorbed'.'a50d9922-b0db-4ec3-b500-9891010d657c' {

                                ref :>> involved = 'eRod_Autonomous_Vehicle_2024 Project'::'eRod_Autonomous_Vehicle_2024'::'Physical Architecture'::'Physical Functions'::'Root Physical Function'.'4deab054-027c-43d9-bdcb-0acc6b2bbd1e';

                            } 
                        ref action 'a50d9922-b0db-4ec3-b500-9891010d657c' = 'eRod_Autonomous_Vehicle_2024 Project'::'eRod_Autonomous_Vehicle_2024'::'Physical Architecture'::'Physical Functions'::'Root Physical Function'.'Transfer power to Axies'; 
                        connection '4d6aa779-d350-4572-96c4-6682330fe48e' : FunctionalChainInvolvementLink 
                            connect source ::> 'eRod_Autonomous_Vehicle_2024 Project'::'eRod_Autonomous_Vehicle_2024'::'Physical Architecture'::'Physical Functions'::'Root Physical Function'.'Car racing absorbed'.'a50d9922-b0db-4ec3-b500-9891010d657c'
                            to  target ::> 'eRod_Autonomous_Vehicle_2024 Project'::'eRod_Autonomous_Vehicle_2024'::'Physical Architecture'::'Physical Functions'::'Root Physical Function'.'Car racing absorbed'.'639d34eb-415a-49fe-b320-99872ee7ed9f' {

                                ref :>> involved = 'eRod_Autonomous_Vehicle_2024 Project'::'eRod_Autonomous_Vehicle_2024'::'Physical Architecture'::'Physical Functions'::'Root Physical Function'.'86db36a6-de52-4275-a1c2-d24a5d1d027e';

                            } 
                        ref action '639d34eb-415a-49fe-b320-99872ee7ed9f' = 'eRod_Autonomous_Vehicle_2024 Project'::'eRod_Autonomous_Vehicle_2024'::'Physical Architecture'::'Physical Functions'::'Root Physical Function'.'Apply rotation on wheels'; 
                        connection 'e77d1ae2-8ba6-4c50-9d2c-a6dccfa8b6ae' : FunctionalChainInvolvementLink 
                            connect source ::> 'eRod_Autonomous_Vehicle_2024 Project'::'eRod_Autonomous_Vehicle_2024'::'Physical Architecture'::'Physical Functions'::'Root Physical Function'.'Car racing absorbed'.'639d34eb-415a-49fe-b320-99872ee7ed9f'
                            to  target ::> 'eRod_Autonomous_Vehicle_2024 Project'::'eRod_Autonomous_Vehicle_2024'::'Physical Architecture'::'Physical Functions'::'Root Physical Function'.'Car racing absorbed'.'e9e43356-c05b-4196-b77c-aa44f6950f1d' {

                                ref :>> involved = 'eRod_Autonomous_Vehicle_2024 Project'::'eRod_Autonomous_Vehicle_2024'::'Physical Architecture'::'Physical Functions'::'Root Physical Function'.'d355c232-2f84-4da6-88be-ea3b3e3927fd';

                            } 
                        ref action 'e9e43356-c05b-4196-b77c-aa44f6950f1d' = 'eRod_Autonomous_Vehicle_2024 Project'::'eRod_Autonomous_Vehicle_2024'::'Physical Architecture'::'Physical Functions'::'Root Physical Function'.'Split 25'; 
                        connection '1c6007e1-d5b5-41df-8f9a-4e997e24b08f' : FunctionalChainInvolvementLink 
                            connect source ::> 'eRod_Autonomous_Vehicle_2024 Project'::'eRod_Autonomous_Vehicle_2024'::'Physical Architecture'::'Physical Functions'::'Root Physical Function'.'Car racing absorbed'.'e9e43356-c05b-4196-b77c-aa44f6950f1d'
                            to  target ::> 'eRod_Autonomous_Vehicle_2024 Project'::'eRod_Autonomous_Vehicle_2024'::'Physical Architecture'::'Physical Functions'::'Root Physical Function'.'Car racing absorbed'.'21550f7b-6094-47eb-8661-1659df4b7e67' {

                                ref :>> involved = 'eRod_Autonomous_Vehicle_2024 Project'::'eRod_Autonomous_Vehicle_2024'::'Physical Architecture'::'Physical Functions'::'Root Physical Function'.'bba22ee9-6f29-4047-a51e-4586c707a2ab';

                            } 
                        ref action '21550f7b-6094-47eb-8661-1659df4b7e67' = 'eRod_Autonomous_Vehicle_2024 Project'::'eRod_Autonomous_Vehicle_2024'::'Physical Architecture'::'Physical Functions'::'Root Physical Function'.'Deaccelerate'; 
                        connection '2f2c9f0e-cda4-467c-a50b-de12d6ecf893' : FunctionalChainInvolvementLink 
                            connect source ::> 'eRod_Autonomous_Vehicle_2024 Project'::'eRod_Autonomous_Vehicle_2024'::'Physical Architecture'::'Physical Functions'::'Root Physical Function'.'Car racing absorbed'.'21550f7b-6094-47eb-8661-1659df4b7e67'
                            to  target ::> 'eRod_Autonomous_Vehicle_2024 Project'::'eRod_Autonomous_Vehicle_2024'::'Physical Architecture'::'Physical Functions'::'Root Physical Function'.'Car racing absorbed'.'e739e143-84b2-4559-8e8f-f9c20e1c0bc9' {

                                ref :>> involved = 'eRod_Autonomous_Vehicle_2024 Project'::'eRod_Autonomous_Vehicle_2024'::'Physical Architecture'::'Physical Functions'::'Root Physical Function'.'1bc640fb-b164-4519-b71d-d0dd4c284f64';

                            } 
                        ref action 'e739e143-84b2-4559-8e8f-f9c20e1c0bc9' = 'eRod_Autonomous_Vehicle_2024 Project'::'eRod_Autonomous_Vehicle_2024'::'Physical Architecture'::'Physical Functions'::'Root Physical Function'.'Stop'; 
                        connection '6dbc9fb1-ed27-4b2c-a12b-ceaa936fc9c3' : FunctionalChainInvolvementLink 
                            connect source ::> 'eRod_Autonomous_Vehicle_2024 Project'::'eRod_Autonomous_Vehicle_2024'::'Physical Architecture'::'Physical Functions'::'Root Physical Function'.'Car racing absorbed'.'e739e143-84b2-4559-8e8f-f9c20e1c0bc9'
                            to  target ::> 'eRod_Autonomous_Vehicle_2024 Project'::'eRod_Autonomous_Vehicle_2024'::'Physical Architecture'::'Physical Functions'::'Root Physical Function'.'Car racing absorbed'.'ba97db70-9613-4d22-a99c-e4ab74447036' {

                                ref :>> involved = 'eRod_Autonomous_Vehicle_2024 Project'::'eRod_Autonomous_Vehicle_2024'::'Physical Architecture'::'Physical Functions'::'Root Physical Function'.'9b4000bd-c473-4c80-a275-48cb0e12156f';

                            } 
                        ref action 'ba97db70-9613-4d22-a99c-e4ab74447036' = 'eRod_Autonomous_Vehicle_2024 Project'::'eRod_Autonomous_Vehicle_2024'::'Physical Architecture'::'Physical Functions'::'Root Physical Function'.'Car racing experience absorbed'; 
                         
                    }  
                    action 'Software update' : FunctionalChain  { 
                        @CapellaID { eid = "0266a9ae-823d-43d8-876f-9b6d29d41081"; } 
                        attribute :>> kind = FunctionalChainKind::SIMPLE; 
                        ref action 'edfe77d5-acac-4fe7-bde8-ac4a58df5df3' = 'eRod_Autonomous_Vehicle_2024 Project'::'eRod_Autonomous_Vehicle_2024'::'Physical Architecture'::'Physical Functions'::'Root Physical Function'.'Get Software-update'; 
                        connection '4e7f89df-6da1-4b14-b44f-bec83cee4743' : FunctionalChainInvolvementLink 
                            connect source ::> 'eRod_Autonomous_Vehicle_2024 Project'::'eRod_Autonomous_Vehicle_2024'::'Physical Architecture'::'Physical Functions'::'Root Physical Function'.'Software update'.'edfe77d5-acac-4fe7-bde8-ac4a58df5df3'
                            to  target ::> 'eRod_Autonomous_Vehicle_2024 Project'::'eRod_Autonomous_Vehicle_2024'::'Physical Architecture'::'Physical Functions'::'Root Physical Function'.'Software update'.'9eefe45c-9fb5-4220-ad98-3bcb7c79b077' {

                                ref :>> involved = 'eRod_Autonomous_Vehicle_2024 Project'::'eRod_Autonomous_Vehicle_2024'::'Physical Architecture'::'Physical Functions'::'Root Physical Function'.'f6baab41-8911-4e66-8f00-539758ee0712';

                            } 
                        ref action '9eefe45c-9fb5-4220-ad98-3bcb7c79b077' = 'eRod_Autonomous_Vehicle_2024 Project'::'eRod_Autonomous_Vehicle_2024'::'Physical Architecture'::'Physical Functions'::'Root Physical Function'.'Improve motor performance'; 
                        connection 'dda13aa4-1eb4-4952-8421-ddf45d156ac1' : FunctionalChainInvolvementLink 
                            connect source ::> 'eRod_Autonomous_Vehicle_2024 Project'::'eRod_Autonomous_Vehicle_2024'::'Physical Architecture'::'Physical Functions'::'Root Physical Function'.'Software update'.'9eefe45c-9fb5-4220-ad98-3bcb7c79b077'
                            to  target ::> 'eRod_Autonomous_Vehicle_2024 Project'::'eRod_Autonomous_Vehicle_2024'::'Physical Architecture'::'Physical Functions'::'Root Physical Function'.'Software update'.'0dd92e15-d2ac-4ab6-a3b5-80e6b6ca8dd6' {

                                ref :>> involved = 'eRod_Autonomous_Vehicle_2024 Project'::'eRod_Autonomous_Vehicle_2024'::'Physical Architecture'::'Physical Functions'::'Root Physical Function'.'ee196aea-0c20-4dac-8b1c-fdcbfc3fa9b4';

                            } 
                        ref action '0dd92e15-d2ac-4ab6-a3b5-80e6b6ca8dd6' = 'eRod_Autonomous_Vehicle_2024 Project'::'eRod_Autonomous_Vehicle_2024'::'Physical Architecture'::'Physical Functions'::'Root Physical Function'.'Controll temperature'.'Limit power'; 
                        connection 'e42eb0d4-51a9-4d21-991a-a92df636aa1e' : FunctionalChainInvolvementLink 
                            connect source ::> 'eRod_Autonomous_Vehicle_2024 Project'::'eRod_Autonomous_Vehicle_2024'::'Physical Architecture'::'Physical Functions'::'Root Physical Function'.'Software update'.'0dd92e15-d2ac-4ab6-a3b5-80e6b6ca8dd6'
                            to  target ::> 'eRod_Autonomous_Vehicle_2024 Project'::'eRod_Autonomous_Vehicle_2024'::'Physical Architecture'::'Physical Functions'::'Root Physical Function'.'Software update'.'9c46eae0-da40-4214-881a-eb67d4ab27bb' {

                                ref :>> involved = 'eRod_Autonomous_Vehicle_2024 Project'::'eRod_Autonomous_Vehicle_2024'::'Physical Architecture'::'Physical Functions'::'Root Physical Function'.'e6396c65-fc89-49bd-9e09-86f944ff82c8';

                            } 
                        ref action '9c46eae0-da40-4214-881a-eb67d4ab27bb' = 'eRod_Autonomous_Vehicle_2024 Project'::'eRod_Autonomous_Vehicle_2024'::'Physical Architecture'::'Physical Functions'::'Root Physical Function'.'deliver mechanical power'; 
                        connection '43cbbe6a-c891-47fd-b684-7f3f1159ce17' : FunctionalChainInvolvementLink 
                            connect source ::> 'eRod_Autonomous_Vehicle_2024 Project'::'eRod_Autonomous_Vehicle_2024'::'Physical Architecture'::'Physical Functions'::'Root Physical Function'.'Software update'.'9c46eae0-da40-4214-881a-eb67d4ab27bb'
                            to  target ::> 'eRod_Autonomous_Vehicle_2024 Project'::'eRod_Autonomous_Vehicle_2024'::'Physical Architecture'::'Physical Functions'::'Root Physical Function'.'Software update'.'f771dc33-11d2-46c0-a73e-0eeb87bb09d8' {

                                ref :>> involved = 'eRod_Autonomous_Vehicle_2024 Project'::'eRod_Autonomous_Vehicle_2024'::'Physical Architecture'::'Physical Functions'::'Root Physical Function'.'4deab054-027c-43d9-bdcb-0acc6b2bbd1e';

                            } 
                        ref action 'f771dc33-11d2-46c0-a73e-0eeb87bb09d8' = 'eRod_Autonomous_Vehicle_2024 Project'::'eRod_Autonomous_Vehicle_2024'::'Physical Architecture'::'Physical Functions'::'Root Physical Function'.'Transfer power to Axies'; 
                        connection 'a436b635-7fac-4f78-aae4-b2f4b410fb4c' : FunctionalChainInvolvementLink 
                            connect source ::> 'eRod_Autonomous_Vehicle_2024 Project'::'eRod_Autonomous_Vehicle_2024'::'Physical Architecture'::'Physical Functions'::'Root Physical Function'.'Software update'.'f771dc33-11d2-46c0-a73e-0eeb87bb09d8'
                            to  target ::> 'eRod_Autonomous_Vehicle_2024 Project'::'eRod_Autonomous_Vehicle_2024'::'Physical Architecture'::'Physical Functions'::'Root Physical Function'.'Software update'.'0732c038-7e86-492c-bd06-7ec48c33f351' {

                                ref :>> involved = 'eRod_Autonomous_Vehicle_2024 Project'::'eRod_Autonomous_Vehicle_2024'::'Physical Architecture'::'Physical Functions'::'Root Physical Function'.'86db36a6-de52-4275-a1c2-d24a5d1d027e';

                            } 
                        ref action '0732c038-7e86-492c-bd06-7ec48c33f351' = 'eRod_Autonomous_Vehicle_2024 Project'::'eRod_Autonomous_Vehicle_2024'::'Physical Architecture'::'Physical Functions'::'Root Physical Function'.'Apply rotation on wheels'; 
                        connection 'e3e1632c-7337-4e5d-aed3-23dcbe6521af' : FunctionalChainInvolvementLink 
                            connect source ::> 'eRod_Autonomous_Vehicle_2024 Project'::'eRod_Autonomous_Vehicle_2024'::'Physical Architecture'::'Physical Functions'::'Root Physical Function'.'Software update'.'0732c038-7e86-492c-bd06-7ec48c33f351'
                            to  target ::> 'eRod_Autonomous_Vehicle_2024 Project'::'eRod_Autonomous_Vehicle_2024'::'Physical Architecture'::'Physical Functions'::'Root Physical Function'.'Software update'.'7ac41184-3c52-47e2-be19-a7851f4b3c35' {

                                ref :>> involved = 'eRod_Autonomous_Vehicle_2024 Project'::'eRod_Autonomous_Vehicle_2024'::'Physical Architecture'::'Physical Functions'::'Root Physical Function'.'d355c232-2f84-4da6-88be-ea3b3e3927fd';

                            } 
                        ref action '7ac41184-3c52-47e2-be19-a7851f4b3c35' = 'eRod_Autonomous_Vehicle_2024 Project'::'eRod_Autonomous_Vehicle_2024'::'Physical Architecture'::'Physical Functions'::'Root Physical Function'.'Split 25'; 
                        connection 'ea4988d0-da75-4c1e-a825-0fc61ea51384' : FunctionalChainInvolvementLink 
                            connect source ::> 'eRod_Autonomous_Vehicle_2024 Project'::'eRod_Autonomous_Vehicle_2024'::'Physical Architecture'::'Physical Functions'::'Root Physical Function'.'Software update'.'7ac41184-3c52-47e2-be19-a7851f4b3c35'
                            to  target ::> 'eRod_Autonomous_Vehicle_2024 Project'::'eRod_Autonomous_Vehicle_2024'::'Physical Architecture'::'Physical Functions'::'Root Physical Function'.'Software update'.'d3b716b8-4716-4e1c-a2c5-fd3eee610a97' {

                                ref :>> involved = 'eRod_Autonomous_Vehicle_2024 Project'::'eRod_Autonomous_Vehicle_2024'::'Physical Architecture'::'Physical Functions'::'Root Physical Function'.'f39aa588-fe27-4554-82db-26cf09846ede';

                            } 
                        ref action 'd3b716b8-4716-4e1c-a2c5-fd3eee610a97' = 'eRod_Autonomous_Vehicle_2024 Project'::'eRod_Autonomous_Vehicle_2024'::'Physical Architecture'::'Physical Functions'::'Root Physical Function'.'Sporty drive'; 
                         
                    }  
                    action 'Vehicle Steering' : FunctionalChain  { 
                        @CapellaID { eid = "b0333614-4f4f-4a8a-bf61-68eab1ed1b5b"; } 
                        attribute :>> kind = FunctionalChainKind::SIMPLE; 
                        connection 'e62e595e-4a63-4fdf-8a1d-8b1489581b12' : FunctionalChainInvolvementLink 
                            connect source ::> 'eRod_Autonomous_Vehicle_2024 Project'::'eRod_Autonomous_Vehicle_2024'::'Physical Architecture'::'Physical Functions'::'Root Physical Function'.'Vehicle Steering'.'ea6c031a-92c3-4cde-80f6-5b607aafeafc'
                            to  target ::> 'eRod_Autonomous_Vehicle_2024 Project'::'eRod_Autonomous_Vehicle_2024'::'Physical Architecture'::'Physical Functions'::'Root Physical Function'.'Vehicle Steering'.'9cee342b-685d-4b15-8e15-99a10d6acfed' {

                                ref :>> involved = 'eRod_Autonomous_Vehicle_2024 Project'::'eRod_Autonomous_Vehicle_2024'::'Physical Architecture'::'Physical Functions'::'Root Physical Function'.'9a080694-6c18-47e9-9819-30442b7aaa82';

                            } 
                        ref action 'ea6c031a-92c3-4cde-80f6-5b607aafeafc' = 'eRod_Autonomous_Vehicle_2024 Project'::'eRod_Autonomous_Vehicle_2024'::'Physical Architecture'::'Physical Functions'::'Root Physical Function'.'Drive vehicle'; 
                        connection '37e22c49-bb60-499d-a7d4-1e826acf2a9c' : FunctionalChainInvolvementLink 
                            connect source ::> 'eRod_Autonomous_Vehicle_2024 Project'::'eRod_Autonomous_Vehicle_2024'::'Physical Architecture'::'Physical Functions'::'Root Physical Function'.'Vehicle Steering'.'d6cf8cb9-7ed3-42d6-91ea-34c8e22d371f'
                            to  target ::> 'eRod_Autonomous_Vehicle_2024 Project'::'eRod_Autonomous_Vehicle_2024'::'Physical Architecture'::'Physical Functions'::'Root Physical Function'.'Vehicle Steering'.'bddc0b59-884d-43c2-9edc-fe82a9a5b217' {

                                ref :>> involved = 'eRod_Autonomous_Vehicle_2024 Project'::'eRod_Autonomous_Vehicle_2024'::'Physical Architecture'::'Physical Functions'::'Root Physical Function'.'2e63b9b6-b395-4be2-bd4a-aef1e86e68e5';

                            } 
                        ref action 'bddc0b59-884d-43c2-9edc-fe82a9a5b217' = 'eRod_Autonomous_Vehicle_2024 Project'::'eRod_Autonomous_Vehicle_2024'::'Physical Architecture'::'Physical Functions'::'Root Physical Function'.'Resist Front Wheels'; 
                        ref action '9cee342b-685d-4b15-8e15-99a10d6acfed' = 'eRod_Autonomous_Vehicle_2024 Project'::'eRod_Autonomous_Vehicle_2024'::'Physical Architecture'::'Physical Functions'::'Root Physical Function'.'Steer Wheels'.'Measure steering angle'; 
                        ref action 'b5724852-4583-48e8-83bb-ff746ee5d1f4' = 'eRod_Autonomous_Vehicle_2024 Project'::'eRod_Autonomous_Vehicle_2024'::'Physical Architecture'::'Physical Functions'::'Root Physical Function'.'Steer Wheels'.'Assist steering'; 
                        ref action '4c789f3b-e1ff-4dc4-a2ad-3c0bd38ff77b' = 'eRod_Autonomous_Vehicle_2024 Project'::'eRod_Autonomous_Vehicle_2024'::'Physical Architecture'::'Physical Functions'::'Root Physical Function'.'Steer Wheels'.'Measure steering force'; 
                        connection '01d6f202-98b1-4e92-bd99-2002c6820448' : FunctionalChainInvolvementLink 
                            connect source ::> 'eRod_Autonomous_Vehicle_2024 Project'::'eRod_Autonomous_Vehicle_2024'::'Physical Architecture'::'Physical Functions'::'Root Physical Function'.'Vehicle Steering'.'ea6c031a-92c3-4cde-80f6-5b607aafeafc'
                            to  target ::> 'eRod_Autonomous_Vehicle_2024 Project'::'eRod_Autonomous_Vehicle_2024'::'Physical Architecture'::'Physical Functions'::'Root Physical Function'.'Vehicle Steering'.'4c789f3b-e1ff-4dc4-a2ad-3c0bd38ff77b' {

                                ref :>> involved = 'eRod_Autonomous_Vehicle_2024 Project'::'eRod_Autonomous_Vehicle_2024'::'Physical Architecture'::'Physical Functions'::'Root Physical Function'.'150f9456-b1c3-47b1-95df-79c543bf5015';

                            } 
                        ref action 'ff95a167-1e64-496a-84b6-486640ade318' = 'eRod_Autonomous_Vehicle_2024 Project'::'eRod_Autonomous_Vehicle_2024'::'Physical Architecture'::'Physical Functions'::'Root Physical Function'.'Steer Wheels'.'Torque steer compensation (TSC)'; 
                        connection '908dca4b-a5a0-45e0-856c-b629a9b65977' : FunctionalChainInvolvementLink 
                            connect source ::> 'eRod_Autonomous_Vehicle_2024 Project'::'eRod_Autonomous_Vehicle_2024'::'Physical Architecture'::'Physical Functions'::'Root Physical Function'.'Vehicle Steering'.'4c789f3b-e1ff-4dc4-a2ad-3c0bd38ff77b'
                            to  target ::> 'eRod_Autonomous_Vehicle_2024 Project'::'eRod_Autonomous_Vehicle_2024'::'Physical Architecture'::'Physical Functions'::'Root Physical Function'.'Vehicle Steering'.'ff95a167-1e64-496a-84b6-486640ade318' {

                                ref :>> involved = 'eRod_Autonomous_Vehicle_2024 Project'::'eRod_Autonomous_Vehicle_2024'::'Physical Architecture'::'Physical Functions'::'Root Physical Function'.'6b77677c-6a80-4a58-a5ea-6922399b4ff9';

                            } 
                        connection '509f256c-299f-4222-9740-9e1f610a4cef' : FunctionalChainInvolvementLink 
                            connect source ::> 'eRod_Autonomous_Vehicle_2024 Project'::'eRod_Autonomous_Vehicle_2024'::'Physical Architecture'::'Physical Functions'::'Root Physical Function'.'Vehicle Steering'.'9cee342b-685d-4b15-8e15-99a10d6acfed'
                            to  target ::> 'eRod_Autonomous_Vehicle_2024 Project'::'eRod_Autonomous_Vehicle_2024'::'Physical Architecture'::'Physical Functions'::'Root Physical Function'.'Vehicle Steering'.'ff95a167-1e64-496a-84b6-486640ade318' {

                                ref :>> involved = 'eRod_Autonomous_Vehicle_2024 Project'::'eRod_Autonomous_Vehicle_2024'::'Physical Architecture'::'Physical Functions'::'Root Physical Function'.'Steer Wheels'.'73d30128-b552-4b75-a646-c889356202be';

                            } 
                        connection '7a4141bc-15c3-4798-a80b-feb639f53568' : FunctionalChainInvolvementLink 
                            connect source ::> 'eRod_Autonomous_Vehicle_2024 Project'::'eRod_Autonomous_Vehicle_2024'::'Physical Architecture'::'Physical Functions'::'Root Physical Function'.'Vehicle Steering'.'ff95a167-1e64-496a-84b6-486640ade318'
                            to  target ::> 'eRod_Autonomous_Vehicle_2024 Project'::'eRod_Autonomous_Vehicle_2024'::'Physical Architecture'::'Physical Functions'::'Root Physical Function'.'Vehicle Steering'.'b5724852-4583-48e8-83bb-ff746ee5d1f4' {

                                ref :>> involved = 'eRod_Autonomous_Vehicle_2024 Project'::'eRod_Autonomous_Vehicle_2024'::'Physical Architecture'::'Physical Functions'::'Root Physical Function'.'9d9dee37-2079-419b-b8a5-dd75d6999ad4';

                            } 
                        ref action 'd6cf8cb9-7ed3-42d6-91ea-34c8e22d371f' = 'eRod_Autonomous_Vehicle_2024 Project'::'eRod_Autonomous_Vehicle_2024'::'Physical Architecture'::'Physical Functions'::'Root Physical Function'.'Steer Wheels'.'Force to Road Left Front'; 
                        ref action '6e0a94c6-9fea-474b-b1f5-20f2cfb838f3' = 'eRod_Autonomous_Vehicle_2024 Project'::'eRod_Autonomous_Vehicle_2024'::'Physical Architecture'::'Physical Functions'::'Root Physical Function'.'Steer Wheels'.'Transmit Left Force'; 
                        connection 'd0fa6cbc-8c5e-48ee-a870-86ac609f11a3' : FunctionalChainInvolvementLink 
                            connect source ::> 'eRod_Autonomous_Vehicle_2024 Project'::'eRod_Autonomous_Vehicle_2024'::'Physical Architecture'::'Physical Functions'::'Root Physical Function'.'Vehicle Steering'.'b5724852-4583-48e8-83bb-ff746ee5d1f4'
                            to  target ::> 'eRod_Autonomous_Vehicle_2024 Project'::'eRod_Autonomous_Vehicle_2024'::'Physical Architecture'::'Physical Functions'::'Root Physical Function'.'Vehicle Steering'.'6e0a94c6-9fea-474b-b1f5-20f2cfb838f3' {

                                ref :>> involved = 'eRod_Autonomous_Vehicle_2024 Project'::'eRod_Autonomous_Vehicle_2024'::'Physical Architecture'::'Physical Functions'::'Root Physical Function'.'Steer Wheels'.'2a944e7a-8965-4971-870b-df89fc55c7dd';

                            } 
                        ref action 'f09d35c8-0293-496b-84ab-ba5dd8c9e0c8' = 'eRod_Autonomous_Vehicle_2024 Project'::'eRod_Autonomous_Vehicle_2024'::'Physical Architecture'::'Physical Functions'::'Root Physical Function'.'Steer Wheels'.'Transmit Right Force'; 
                        connection '2e06be13-de00-457f-8b4e-b67af6a00ca5' : FunctionalChainInvolvementLink 
                            connect source ::> 'eRod_Autonomous_Vehicle_2024 Project'::'eRod_Autonomous_Vehicle_2024'::'Physical Architecture'::'Physical Functions'::'Root Physical Function'.'Vehicle Steering'.'b5724852-4583-48e8-83bb-ff746ee5d1f4'
                            to  target ::> 'eRod_Autonomous_Vehicle_2024 Project'::'eRod_Autonomous_Vehicle_2024'::'Physical Architecture'::'Physical Functions'::'Root Physical Function'.'Vehicle Steering'.'f09d35c8-0293-496b-84ab-ba5dd8c9e0c8' {

                                ref :>> involved = 'eRod_Autonomous_Vehicle_2024 Project'::'eRod_Autonomous_Vehicle_2024'::'Physical Architecture'::'Physical Functions'::'Root Physical Function'.'Steer Wheels'.'872387bc-c61f-4975-bf12-dd220518b44d';

                            } 
                        connection '70e07b2e-6ffe-4175-b697-a094b7b1c874' : FunctionalChainInvolvementLink 
                            connect source ::> 'eRod_Autonomous_Vehicle_2024 Project'::'eRod_Autonomous_Vehicle_2024'::'Physical Architecture'::'Physical Functions'::'Root Physical Function'.'Vehicle Steering'.'6e0a94c6-9fea-474b-b1f5-20f2cfb838f3'
                            to  target ::> 'eRod_Autonomous_Vehicle_2024 Project'::'eRod_Autonomous_Vehicle_2024'::'Physical Architecture'::'Physical Functions'::'Root Physical Function'.'Vehicle Steering'.'d6cf8cb9-7ed3-42d6-91ea-34c8e22d371f' {

                                ref :>> involved = 'eRod_Autonomous_Vehicle_2024 Project'::'eRod_Autonomous_Vehicle_2024'::'Physical Architecture'::'Physical Functions'::'Root Physical Function'.'Steer Wheels'.'4ab23e81-867a-4e42-b992-a665c9ce5324';

                            } 
                        ref action '54f60bb9-3642-49da-80d3-6127c7145e99' = 'eRod_Autonomous_Vehicle_2024 Project'::'eRod_Autonomous_Vehicle_2024'::'Physical Architecture'::'Physical Functions'::'Root Physical Function'.'Steer Wheels'.'Force to Road Right Front'; 
                        connection '6e37564b-473c-4ffd-a282-bd1b7ece5f5b' : FunctionalChainInvolvementLink 
                            connect source ::> 'eRod_Autonomous_Vehicle_2024 Project'::'eRod_Autonomous_Vehicle_2024'::'Physical Architecture'::'Physical Functions'::'Root Physical Function'.'Vehicle Steering'.'f09d35c8-0293-496b-84ab-ba5dd8c9e0c8'
                            to  target ::> 'eRod_Autonomous_Vehicle_2024 Project'::'eRod_Autonomous_Vehicle_2024'::'Physical Architecture'::'Physical Functions'::'Root Physical Function'.'Vehicle Steering'.'54f60bb9-3642-49da-80d3-6127c7145e99' {

                                ref :>> involved = 'eRod_Autonomous_Vehicle_2024 Project'::'eRod_Autonomous_Vehicle_2024'::'Physical Architecture'::'Physical Functions'::'Root Physical Function'.'Steer Wheels'.'a9b2c213-d86e-4c47-a6f3-8f6216ccdb49';

                            } 
                        connection '53a0e87b-0924-4c0c-8b18-7d8dbfff649f' : FunctionalChainInvolvementLink 
                            connect source ::> 'eRod_Autonomous_Vehicle_2024 Project'::'eRod_Autonomous_Vehicle_2024'::'Physical Architecture'::'Physical Functions'::'Root Physical Function'.'Vehicle Steering'.'54f60bb9-3642-49da-80d3-6127c7145e99'
                            to  target ::> 'eRod_Autonomous_Vehicle_2024 Project'::'eRod_Autonomous_Vehicle_2024'::'Physical Architecture'::'Physical Functions'::'Root Physical Function'.'Vehicle Steering'.'bddc0b59-884d-43c2-9edc-fe82a9a5b217' {

                                ref :>> involved = 'eRod_Autonomous_Vehicle_2024 Project'::'eRod_Autonomous_Vehicle_2024'::'Physical Architecture'::'Physical Functions'::'Root Physical Function'.'05bbbd1d-69e8-4e7d-bddf-c01c48911cd4';

                            } 
                         
                    }  
                    action 'Lane Keep Assist (LKA)' : FunctionalChain  { 
                        @CapellaID { eid = "b6e56729-741c-4ba3-b7ce-635b84482573"; } 
                        attribute :>> kind = FunctionalChainKind::SIMPLE; 
                        connection 'ec258b04-f2f8-432e-90b9-b25a8db53c5b' : FunctionalChainInvolvementLink 
                            connect source ::> 'eRod_Autonomous_Vehicle_2024 Project'::'eRod_Autonomous_Vehicle_2024'::'Physical Architecture'::'Physical Functions'::'Root Physical Function'.'Lane Keep Assist (LKA)'.'6720c7fa-3745-437b-a710-5eb987dfb4c4'
                            to  target ::> 'eRod_Autonomous_Vehicle_2024 Project'::'eRod_Autonomous_Vehicle_2024'::'Physical Architecture'::'Physical Functions'::'Root Physical Function'.'Lane Keep Assist (LKA)'.'b0099245-4d4d-4437-b100-21981c0024b3' {

                                ref :>> involved = 'eRod_Autonomous_Vehicle_2024 Project'::'eRod_Autonomous_Vehicle_2024'::'Physical Architecture'::'Physical Functions'::'Root Physical Function'.'bb3291df-08bb-4dda-bb17-582231a87c97';

                            } 
                        ref action '6720c7fa-3745-437b-a710-5eb987dfb4c4' = 'eRod_Autonomous_Vehicle_2024 Project'::'eRod_Autonomous_Vehicle_2024'::'Physical Architecture'::'Physical Functions'::'Root Physical Function'.'Provide road markers'; 
                        connection '99ac1749-13c5-4b6a-bc68-959603df0175' : FunctionalChainInvolvementLink 
                            connect source ::> 'eRod_Autonomous_Vehicle_2024 Project'::'eRod_Autonomous_Vehicle_2024'::'Physical Architecture'::'Physical Functions'::'Root Physical Function'.'Lane Keep Assist (LKA)'.'b486b7d2-0b59-4b99-bb3d-2d773bbf5372'
                            to  target ::> 'eRod_Autonomous_Vehicle_2024 Project'::'eRod_Autonomous_Vehicle_2024'::'Physical Architecture'::'Physical Functions'::'Root Physical Function'.'Lane Keep Assist (LKA)'.'e7e8f5ae-9c33-4c42-a77b-dfbce783f84f' {

                                ref :>> involved = 'eRod_Autonomous_Vehicle_2024 Project'::'eRod_Autonomous_Vehicle_2024'::'Physical Architecture'::'Physical Functions'::'Root Physical Function'.'39cf23bb-f26c-40c2-a631-9155541fab5d';

                            } 
                        ref action 'e7e8f5ae-9c33-4c42-a77b-dfbce783f84f' = 'eRod_Autonomous_Vehicle_2024 Project'::'eRod_Autonomous_Vehicle_2024'::'Physical Architecture'::'Physical Functions'::'Root Physical Function'.'Steer Wheels'.'Automatic Steering'; 
                        ref action 'b0099245-4d4d-4437-b100-21981c0024b3' = 'eRod_Autonomous_Vehicle_2024 Project'::'eRod_Autonomous_Vehicle_2024'::'Physical Architecture'::'Physical Functions'::'Root Physical Function'.'Detect road'.'Capture view'; 
                        ref action 'a5d1cb33-bfa5-495d-a37d-2115f9edb4e9' = 'eRod_Autonomous_Vehicle_2024 Project'::'eRod_Autonomous_Vehicle_2024'::'Physical Architecture'::'Physical Functions'::'Root Physical Function'.'Detect road'.'Image fusion'; 
                        connection '2b00a560-c813-48b8-a10b-af3a34c7beb6' : FunctionalChainInvolvementLink 
                            connect source ::> 'eRod_Autonomous_Vehicle_2024 Project'::'eRod_Autonomous_Vehicle_2024'::'Physical Architecture'::'Physical Functions'::'Root Physical Function'.'Lane Keep Assist (LKA)'.'b0099245-4d4d-4437-b100-21981c0024b3'
                            to  target ::> 'eRod_Autonomous_Vehicle_2024 Project'::'eRod_Autonomous_Vehicle_2024'::'Physical Architecture'::'Physical Functions'::'Root Physical Function'.'Lane Keep Assist (LKA)'.'a5d1cb33-bfa5-495d-a37d-2115f9edb4e9' {

                                ref :>> involved = 'eRod_Autonomous_Vehicle_2024 Project'::'eRod_Autonomous_Vehicle_2024'::'Physical Architecture'::'Physical Functions'::'Root Physical Function'.'Detect road'.'96bd69e2-5156-4cb4-8fff-fbf0bbbf8206';

                            } 
                        ref action 'b486b7d2-0b59-4b99-bb3d-2d773bbf5372' = 'eRod_Autonomous_Vehicle_2024 Project'::'eRod_Autonomous_Vehicle_2024'::'Physical Architecture'::'Physical Functions'::'Root Physical Function'.'Detect road'.'Detect path'; 
                        connection '3d7e8722-8879-46bd-9dac-6c1bf2797ae5' : FunctionalChainInvolvementLink 
                            connect source ::> 'eRod_Autonomous_Vehicle_2024 Project'::'eRod_Autonomous_Vehicle_2024'::'Physical Architecture'::'Physical Functions'::'Root Physical Function'.'Lane Keep Assist (LKA)'.'a5d1cb33-bfa5-495d-a37d-2115f9edb4e9'
                            to  target ::> 'eRod_Autonomous_Vehicle_2024 Project'::'eRod_Autonomous_Vehicle_2024'::'Physical Architecture'::'Physical Functions'::'Root Physical Function'.'Lane Keep Assist (LKA)'.'b486b7d2-0b59-4b99-bb3d-2d773bbf5372' {

                                ref :>> involved = 'eRod_Autonomous_Vehicle_2024 Project'::'eRod_Autonomous_Vehicle_2024'::'Physical Architecture'::'Physical Functions'::'Root Physical Function'.'4c223d18-1eaf-4293-b5bf-4d114649ab2b';

                            } 
                        ref action '35f192a3-484d-4554-83c9-5ad33e169d50' = 'eRod_Autonomous_Vehicle_2024 Project'::'eRod_Autonomous_Vehicle_2024'::'Physical Architecture'::'Physical Functions'::'Root Physical Function'.'Steer Wheels'.'Torque steer compensation (TSC)'; 
                        connection '67add7e6-913c-407f-b4ad-f6d461d6b177' : FunctionalChainInvolvementLink 
                            connect source ::> 'eRod_Autonomous_Vehicle_2024 Project'::'eRod_Autonomous_Vehicle_2024'::'Physical Architecture'::'Physical Functions'::'Root Physical Function'.'Lane Keep Assist (LKA)'.'e7e8f5ae-9c33-4c42-a77b-dfbce783f84f'
                            to  target ::> 'eRod_Autonomous_Vehicle_2024 Project'::'eRod_Autonomous_Vehicle_2024'::'Physical Architecture'::'Physical Functions'::'Root Physical Function'.'Lane Keep Assist (LKA)'.'35f192a3-484d-4554-83c9-5ad33e169d50' {

                                ref :>> involved = 'eRod_Autonomous_Vehicle_2024 Project'::'eRod_Autonomous_Vehicle_2024'::'Physical Architecture'::'Physical Functions'::'Root Physical Function'.'Steer Wheels'.'4d8fe037-1771-406b-8cb4-b33ea24a9b44';

                            } 
                        ref action 'b5f8475a-e2ee-43e0-90e2-88f2c031477c' = 'eRod_Autonomous_Vehicle_2024 Project'::'eRod_Autonomous_Vehicle_2024'::'Physical Architecture'::'Physical Functions'::'Root Physical Function'.'Steer Wheels'.'Assist steering'; 
                        connection 'cab7778d-3c8a-452e-90ec-cc7bf39fc632' : FunctionalChainInvolvementLink 
                            connect source ::> 'eRod_Autonomous_Vehicle_2024 Project'::'eRod_Autonomous_Vehicle_2024'::'Physical Architecture'::'Physical Functions'::'Root Physical Function'.'Lane Keep Assist (LKA)'.'35f192a3-484d-4554-83c9-5ad33e169d50'
                            to  target ::> 'eRod_Autonomous_Vehicle_2024 Project'::'eRod_Autonomous_Vehicle_2024'::'Physical Architecture'::'Physical Functions'::'Root Physical Function'.'Lane Keep Assist (LKA)'.'b5f8475a-e2ee-43e0-90e2-88f2c031477c' {

                                ref :>> involved = 'eRod_Autonomous_Vehicle_2024 Project'::'eRod_Autonomous_Vehicle_2024'::'Physical Architecture'::'Physical Functions'::'Root Physical Function'.'9d9dee37-2079-419b-b8a5-dd75d6999ad4';

                            } 
                        ref action '96fd20b0-e951-4e31-a1d9-aaba743e56d2' = 'eRod_Autonomous_Vehicle_2024 Project'::'eRod_Autonomous_Vehicle_2024'::'Physical Architecture'::'Physical Functions'::'Root Physical Function'.'Resist Front Wheels'; 
                        connection '3b2c8bad-3b32-42be-9b19-ebdfbd421827' : FunctionalChainInvolvementLink 
                            connect source ::> 'eRod_Autonomous_Vehicle_2024 Project'::'eRod_Autonomous_Vehicle_2024'::'Physical Architecture'::'Physical Functions'::'Root Physical Function'.'Lane Keep Assist (LKA)'.'48cf88b3-5592-43ce-a666-53120505251b'
                            to  target ::> 'eRod_Autonomous_Vehicle_2024 Project'::'eRod_Autonomous_Vehicle_2024'::'Physical Architecture'::'Physical Functions'::'Root Physical Function'.'Lane Keep Assist (LKA)'.'96fd20b0-e951-4e31-a1d9-aaba743e56d2' {

                                ref :>> involved = 'eRod_Autonomous_Vehicle_2024 Project'::'eRod_Autonomous_Vehicle_2024'::'Physical Architecture'::'Physical Functions'::'Root Physical Function'.'2e63b9b6-b395-4be2-bd4a-aef1e86e68e5';

                            } 
                        ref action '48cf88b3-5592-43ce-a666-53120505251b' = 'eRod_Autonomous_Vehicle_2024 Project'::'eRod_Autonomous_Vehicle_2024'::'Physical Architecture'::'Physical Functions'::'Root Physical Function'.'Steer Wheels'.'Force to Road Left Front'; 
                        ref action '06140944-6c65-4981-92e3-955c4962305c' = 'eRod_Autonomous_Vehicle_2024 Project'::'eRod_Autonomous_Vehicle_2024'::'Physical Architecture'::'Physical Functions'::'Root Physical Function'.'Steer Wheels'.'Transmit Left Force'; 
                        connection '4fde10c0-58af-440a-bf94-6d2964ee192a' : FunctionalChainInvolvementLink 
                            connect source ::> 'eRod_Autonomous_Vehicle_2024 Project'::'eRod_Autonomous_Vehicle_2024'::'Physical Architecture'::'Physical Functions'::'Root Physical Function'.'Lane Keep Assist (LKA)'.'b5f8475a-e2ee-43e0-90e2-88f2c031477c'
                            to  target ::> 'eRod_Autonomous_Vehicle_2024 Project'::'eRod_Autonomous_Vehicle_2024'::'Physical Architecture'::'Physical Functions'::'Root Physical Function'.'Lane Keep Assist (LKA)'.'06140944-6c65-4981-92e3-955c4962305c' {

                                ref :>> involved = 'eRod_Autonomous_Vehicle_2024 Project'::'eRod_Autonomous_Vehicle_2024'::'Physical Architecture'::'Physical Functions'::'Root Physical Function'.'Steer Wheels'.'2a944e7a-8965-4971-870b-df89fc55c7dd';

                            } 
                        ref action '398d8712-5be1-490e-84d1-0cc4ee693ec9' = 'eRod_Autonomous_Vehicle_2024 Project'::'eRod_Autonomous_Vehicle_2024'::'Physical Architecture'::'Physical Functions'::'Root Physical Function'.'Steer Wheels'.'Transmit Right Force'; 
                        connection '7be693d6-61d5-4c38-a906-2900823889a3' : FunctionalChainInvolvementLink 
                            connect source ::> 'eRod_Autonomous_Vehicle_2024 Project'::'eRod_Autonomous_Vehicle_2024'::'Physical Architecture'::'Physical Functions'::'Root Physical Function'.'Lane Keep Assist (LKA)'.'b5f8475a-e2ee-43e0-90e2-88f2c031477c'
                            to  target ::> 'eRod_Autonomous_Vehicle_2024 Project'::'eRod_Autonomous_Vehicle_2024'::'Physical Architecture'::'Physical Functions'::'Root Physical Function'.'Lane Keep Assist (LKA)'.'398d8712-5be1-490e-84d1-0cc4ee693ec9' {

                                ref :>> involved = 'eRod_Autonomous_Vehicle_2024 Project'::'eRod_Autonomous_Vehicle_2024'::'Physical Architecture'::'Physical Functions'::'Root Physical Function'.'Steer Wheels'.'872387bc-c61f-4975-bf12-dd220518b44d';

                            } 
                        connection '4481fcfe-c1a7-4b90-952e-b1df1933b4fe' : FunctionalChainInvolvementLink 
                            connect source ::> 'eRod_Autonomous_Vehicle_2024 Project'::'eRod_Autonomous_Vehicle_2024'::'Physical Architecture'::'Physical Functions'::'Root Physical Function'.'Lane Keep Assist (LKA)'.'06140944-6c65-4981-92e3-955c4962305c'
                            to  target ::> 'eRod_Autonomous_Vehicle_2024 Project'::'eRod_Autonomous_Vehicle_2024'::'Physical Architecture'::'Physical Functions'::'Root Physical Function'.'Lane Keep Assist (LKA)'.'48cf88b3-5592-43ce-a666-53120505251b' {

                                ref :>> involved = 'eRod_Autonomous_Vehicle_2024 Project'::'eRod_Autonomous_Vehicle_2024'::'Physical Architecture'::'Physical Functions'::'Root Physical Function'.'Steer Wheels'.'4ab23e81-867a-4e42-b992-a665c9ce5324';

                            } 
                        ref action '469a5c23-4024-4853-a451-ea9604fb32b7' = 'eRod_Autonomous_Vehicle_2024 Project'::'eRod_Autonomous_Vehicle_2024'::'Physical Architecture'::'Physical Functions'::'Root Physical Function'.'Steer Wheels'.'Force to Road Right Front'; 
                        connection '5387c295-b033-4a45-8ae5-82d7a441e222' : FunctionalChainInvolvementLink 
                            connect source ::> 'eRod_Autonomous_Vehicle_2024 Project'::'eRod_Autonomous_Vehicle_2024'::'Physical Architecture'::'Physical Functions'::'Root Physical Function'.'Lane Keep Assist (LKA)'.'398d8712-5be1-490e-84d1-0cc4ee693ec9'
                            to  target ::> 'eRod_Autonomous_Vehicle_2024 Project'::'eRod_Autonomous_Vehicle_2024'::'Physical Architecture'::'Physical Functions'::'Root Physical Function'.'Lane Keep Assist (LKA)'.'469a5c23-4024-4853-a451-ea9604fb32b7' {

                                ref :>> involved = 'eRod_Autonomous_Vehicle_2024 Project'::'eRod_Autonomous_Vehicle_2024'::'Physical Architecture'::'Physical Functions'::'Root Physical Function'.'Steer Wheels'.'a9b2c213-d86e-4c47-a6f3-8f6216ccdb49';

                            } 
                        connection '7eb014e3-85ff-40c3-b869-f76212a55915' : FunctionalChainInvolvementLink 
                            connect source ::> 'eRod_Autonomous_Vehicle_2024 Project'::'eRod_Autonomous_Vehicle_2024'::'Physical Architecture'::'Physical Functions'::'Root Physical Function'.'Lane Keep Assist (LKA)'.'469a5c23-4024-4853-a451-ea9604fb32b7'
                            to  target ::> 'eRod_Autonomous_Vehicle_2024 Project'::'eRod_Autonomous_Vehicle_2024'::'Physical Architecture'::'Physical Functions'::'Root Physical Function'.'Lane Keep Assist (LKA)'.'96fd20b0-e951-4e31-a1d9-aaba743e56d2' {

                                ref :>> involved = 'eRod_Autonomous_Vehicle_2024 Project'::'eRod_Autonomous_Vehicle_2024'::'Physical Architecture'::'Physical Functions'::'Root Physical Function'.'05bbbd1d-69e8-4e7d-bddf-c01c48911cd4';

                            } 
                         
                    }  
                    action 'Drive on a race track' : PhysicalFunction  { 
                        @CapellaID { eid = "344e10e6-9c33-4f4c-b9c0-c5af037fff75"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outCommand' : FunctionOutputPort  { 
                            @CapellaID { eid = "85a6004e-2152-4a91-8326-856452f29dd1"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Drive on a race track'.'outCommand'); 
                    }  
                    action 'Sporty drive' : PhysicalFunction  { 
                        @CapellaID { eid = "fe22378e-3152-4610-8dfc-29b8bfc563d8"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 2' : FunctionOutputPort  { 
                            @CapellaID { eid = "a43da032-832b-4538-9cdb-afe70c66c0fd"; } 
                            attribute :>> isControl = false; 
                            attribute :>> isControlType = false; 
                            attribute :>> kindOfNode = ObjectNodeKind::Unspecified; 
                            attribute :>> ordering = ObjectNodeOrderingKind::FIFO; 
                             
                        }  
                        out port 'FOP 3' : FunctionOutputPort  { 
                            @CapellaID { eid = "ace200bf-610d-4ca7-a81a-0c558bc9113f"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "06d76d48-212d-422d-a801-dcc0d2f8c210"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Sporty drive'.'FOP 2',
                        'eRod_Autonomous_Vehicle_2024 Project'::'eRod_Autonomous_Vehicle_2024'::'Physical Architecture'::'Physical Functions'::'Root Physical Function'.'Sporty drive'.'FOP 3'); 
                        ref :>> inputs =  ('eRod_Autonomous_Vehicle_2024 Project'::'eRod_Autonomous_Vehicle_2024'::'Physical Architecture'::'Physical Functions'::'Root Physical Function'.'Sporty drive'.'FIP 2'); 
                    }  
                    action 'Car racing experience absorbed' : PhysicalFunction  { 
                        @CapellaID { eid = "15cb9c8d-600d-4f7e-9afd-8d4844b5a633"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'inProvide' : FunctionInputPort  { 
                            @CapellaID { eid = "dc2785bb-47a7-43f2-9ca2-15b306d65d4d"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Physical Architecture'::'Physical Functions'::'Root Physical Function'.'Car racing experience absorbed'.'inProvide'); 
                    }  
                    action 'Motor overheating warning ' : PhysicalFunction  { 
                        @CapellaID { eid = "0dbe7e4d-a55e-4081-a9b5-4a37d29da812"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outDisplay' : FunctionOutputPort  { 
                            @CapellaID { eid = "5431f9a8-17d0-43e4-8e34-40d425ca2cdb"; } 
                            attribute :>> isControl = false; 
                            attribute :>> isControlType = false; 
                            attribute :>> kindOfNode = ObjectNodeKind::Unspecified; 
                            attribute :>> ordering = ObjectNodeOrderingKind::FIFO; 
                             
                        }  
                        in port 'inCause' : FunctionInputPort  { 
                            @CapellaID { eid = "c2940ebe-07f0-402d-bb8b-a76410d6733d"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Motor overheating warning '.'outDisplay'); 
                        ref :>> inputs =  ('eRod_Autonomous_Vehicle_2024 Project'::'eRod_Autonomous_Vehicle_2024'::'Physical Architecture'::'Physical Functions'::'Root Physical Function'.'Motor overheating warning '.'inCause'); 
                    }  
                    action 'Software update' : PhysicalFunction  { 
                        @CapellaID { eid = "59b186dc-3011-4e6b-bcff-9163755ef28a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outRe-enable' : FunctionOutputPort  { 
                            @CapellaID { eid = "d4bba26b-9e4d-472b-b7d7-347c6519016a"; } 
                            attribute :>> isControl = false; 
                            attribute :>> isControlType = false; 
                            attribute :>> kindOfNode = ObjectNodeKind::Unspecified; 
                            attribute :>> ordering = ObjectNodeOrderingKind::FIFO; 
                             
                        }  
                        in port 'inFeedback' : FunctionInputPort  { 
                            @CapellaID { eid = "9a390673-7462-4057-814e-685521184f09"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Software update'.'outRe-enable'); 
                        ref :>> inputs =  ('eRod_Autonomous_Vehicle_2024 Project'::'eRod_Autonomous_Vehicle_2024'::'Physical Architecture'::'Physical Functions'::'Root Physical Function'.'Software update'.'inFeedback'); 
                    }  
                    action 'Report issues' : PhysicalFunction  { 
                        @CapellaID { eid = "f643a2db-ad13-42e2-b339-c95a4254de0f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "e1aefb10-0285-49aa-964a-498f621b0685"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "8615dcaa-c1f8-49f6-b968-614a9f66020d"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Report issues'.'FOP 1'); 
                        ref :>> inputs =  ('eRod_Autonomous_Vehicle_2024 Project'::'eRod_Autonomous_Vehicle_2024'::'Physical Architecture'::'Physical Functions'::'Root Physical Function'.'Report issues'.'FIP 1'); 
                    }  
                    action 'Get informed with issues' : PhysicalFunction  { 
                        @CapellaID { eid = "af5d86e3-7b68-4129-838f-f59a8e9f07e9"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "a086186c-b1c2-46cc-82ab-70afc501fe70"; } 
                            attribute :>> isControl = false; 
                            attribute :>> isControlType = false; 
                            attribute :>> kindOfNode = ObjectNodeKind::Unspecified; 
                            attribute :>> ordering = ObjectNodeOrderingKind::FIFO; 
                             
                        }  
                        in port 'inDisplay' : FunctionInputPort  { 
                            @CapellaID { eid = "e87cae86-3e97-4c08-ae5e-01a94eb1e647"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Get informed with issues'.'FOP 1'); 
                        ref :>> inputs =  ('eRod_Autonomous_Vehicle_2024 Project'::'eRod_Autonomous_Vehicle_2024'::'Physical Architecture'::'Physical Functions'::'Root Physical Function'.'Get informed with issues'.'inDisplay'); 
                    }  
                    action 'Deaccelerate' : PhysicalFunction  { 
                        @CapellaID { eid = "e485ce86-54c6-4a66-9263-a059b3aa9294"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "027036a4-8ebe-4f14-b1a7-26285e67fff8"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "023af21d-d6b6-4969-87ba-e3a8fbff2666"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Deaccelerate'.'FOP 1'); 
                        ref :>> inputs =  ('eRod_Autonomous_Vehicle_2024 Project'::'eRod_Autonomous_Vehicle_2024'::'Physical Architecture'::'Physical Functions'::'Root Physical Function'.'Deaccelerate'.'FIP 1'); 
                    }  
                    action 'Stop' : PhysicalFunction  { 
                        @CapellaID { eid = "c024bd0b-722f-4eb3-886b-9a73ceec05e6"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outProvide' : FunctionOutputPort  { 
                            @CapellaID { eid = "a295d2a4-a4a4-4cce-9f26-983347feb6ca"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "43f7a122-a786-4fe8-bd3c-6f3f25712cba"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Stop'.'outProvide'); 
                        ref :>> inputs =  ('eRod_Autonomous_Vehicle_2024 Project'::'eRod_Autonomous_Vehicle_2024'::'Physical Architecture'::'Physical Functions'::'Root Physical Function'.'Stop'.'FIP 1'); 
                    }  
                    action 'Get Software-update' : PhysicalFunction  { 
                        @CapellaID { eid = "afdfa4f6-b966-4999-a29c-6a5928ef4154"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "9535b221-ef25-40e7-9248-8d9389f3e992"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "a02f9015-016f-4b14-a65c-bdc9f9a2ce6d"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Get Software-update'.'FOP 1'); 
                        ref :>> inputs =  ('eRod_Autonomous_Vehicle_2024 Project'::'eRod_Autonomous_Vehicle_2024'::'Physical Architecture'::'Physical Functions'::'Root Physical Function'.'Get Software-update'.'FIP 1'); 
                    }  
                    action 'Transfer Energy' : PhysicalFunction  { 
                        @CapellaID { eid = "f02da1ef-461c-42a3-9c47-3c78fce77fca"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Acquire electrical Energy' : PhysicalFunction  { 
                            @CapellaID { eid = "b73c7118-1630-4449-b881-1ff09153d32a"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "7e7c23e4-542c-4be4-9996-923ad6af3eca"; } 
                                attribute :>> isControl = false; 
                                attribute :>> isControlType = false; 
                                attribute :>> kindOfNode = ObjectNodeKind::Unspecified; 
                                attribute :>> ordering = ObjectNodeOrderingKind::FIFO; 
                                 
                            }  
                            out port 'FOP 2' : FunctionOutputPort  { 
                                @CapellaID { eid = "4e1c8b3b-5fcf-4c1f-b930-efe984a2a869"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "58ce2e9a-c37a-443a-aff1-63778ad60bda"; } 
                                attribute :>> isControl = false; 
                                attribute :>> isControlType = false; 
                                attribute :>> kindOfNode = ObjectNodeKind::Unspecified; 
                                attribute :>> ordering = ObjectNodeOrderingKind::FIFO; 
                                 
                            }  
                            in port 'FIP 2' : FunctionInputPort  { 
                                @CapellaID { eid = "6f200084-99c1-4670-9cf7-6103857d93c0"; } 
                                attribute :>> isControl = false; 
                                attribute :>> isControlType = false; 
                                attribute :>> kindOfNode = ObjectNodeKind::Unspecified; 
                                attribute :>> ordering = ObjectNodeOrderingKind::FIFO; 
                                 
                            }  
                            in port 'FIP 3' : FunctionInputPort  { 
                                @CapellaID { eid = "b02862e3-3522-47d9-8886-f2af466085af"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Physical Architecture'::'Physical Functions'::'Root Physical Function'.'Transfer Energy'.'Acquire electrical Energy'.'FOP 1',
                            'eRod_Autonomous_Vehicle_2024 Project'::'eRod_Autonomous_Vehicle_2024'::'Physical Architecture'::'Physical Functions'::'Root Physical Function'.'Transfer Energy'.'Acquire electrical Energy'.'FOP 2'); 
                            ref :>> inputs =  ('eRod_Autonomous_Vehicle_2024 Project'::'eRod_Autonomous_Vehicle_2024'::'Physical Architecture'::'Physical Functions'::'Root Physical Function'.'Transfer Energy'.'Acquire electrical Energy'.'FIP 1',
                            'eRod_Autonomous_Vehicle_2024 Project'::'eRod_Autonomous_Vehicle_2024'::'Physical Architecture'::'Physical Functions'::'Root Physical Function'.'Transfer Energy'.'Acquire electrical Energy'.'FIP 2',
                            'eRod_Autonomous_Vehicle_2024 Project'::'eRod_Autonomous_Vehicle_2024'::'Physical Architecture'::'Physical Functions'::'Root Physical Function'.'Transfer Energy'.'Acquire electrical Energy'.'FIP 3'); 
                        }  
                        action 'Tranfer electrical energy into mechanical energy' : PhysicalFunction  { 
                            @CapellaID { eid = "2e6246a6-40a4-468e-92e0-7bc49306e4d9"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "0c9cb841-9e61-4f09-ac28-0c62b1e5b209"; } 
                                attribute :>> isControl = false; 
                                attribute :>> isControlType = false; 
                                attribute :>> kindOfNode = ObjectNodeKind::Unspecified; 
                                attribute :>> ordering = ObjectNodeOrderingKind::FIFO; 
                                 
                            }  
                            out port 'FOP 2' : FunctionOutputPort  { 
                                @CapellaID { eid = "32de2469-2dc5-450c-bcf7-af463c139855"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Physical Architecture'::'Physical Functions'::'Root Physical Function'.'Transfer Energy'.'Tranfer electrical energy into mechanical energy'.'FOP 1',
                            'eRod_Autonomous_Vehicle_2024 Project'::'eRod_Autonomous_Vehicle_2024'::'Physical Architecture'::'Physical Functions'::'Root Physical Function'.'Transfer Energy'.'Tranfer electrical energy into mechanical energy'.'FOP 2'); 
                        }  
                        action 'Generate heat' : PhysicalFunction  { 
                            @CapellaID { eid = "cafeaeca-f3b8-4e30-b2ed-6935c9c928ac"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "13e7d3cc-eb3e-40fb-b4cb-5edaaa734abb"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "f361b18a-b057-484a-a1ad-588f89a4b6e2"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Physical Architecture'::'Physical Functions'::'Root Physical Function'.'Transfer Energy'.'Generate heat'.'FOP 1'); 
                            ref :>> inputs =  ('eRod_Autonomous_Vehicle_2024 Project'::'eRod_Autonomous_Vehicle_2024'::'Physical Architecture'::'Physical Functions'::'Root Physical Function'.'Transfer Energy'.'Generate heat'.'FIP 1'); 
                        }  
                        interface 'cdce9058-efed-4b3d-963c-24c533b1ddf2' : FunctionalExchange 
                            connect source ::> 'eRod_Autonomous_Vehicle_2024 Project'::'eRod_Autonomous_Vehicle_2024'::'Physical Architecture'::'Physical Functions'::'Root Physical Function'.'Transfer Energy'.'Tranfer electrical energy into mechanical energy'.'FOP 2'
                            to target ::> 'eRod_Autonomous_Vehicle_2024 Project'::'eRod_Autonomous_Vehicle_2024'::'Physical Architecture'::'Physical Functions'::'Root Physical Function'.'Transfer Energy'.'Generate heat'.'FIP 1' { 
                            @CapellaID { eid = "cdce9058-efed-4b3d-963c-24c533b1ddf2"; } 
                            attribute :>> isMulticast = false; 
                            attribute :>> isMultireceive = false; 
                            attribute :>> kindOfRate = RateKind::Unspecified; 
                            attribute :>> interfaceName = "Energy"; 
                             
                        }  
                         
                        ref :>> ownedFunctions =  ('eRod_Autonomous_Vehicle_2024 Project'::'eRod_Autonomous_Vehicle_2024'::'Physical Architecture'::'Physical Functions'::'Root Physical Function'.'Transfer Energy'.'Acquire electrical Energy',
                        'eRod_Autonomous_Vehicle_2024 Project'::'eRod_Autonomous_Vehicle_2024'::'Physical Architecture'::'Physical Functions'::'Root Physical Function'.'Transfer Energy'.'Tranfer electrical energy into mechanical energy',
                        'eRod_Autonomous_Vehicle_2024 Project'::'eRod_Autonomous_Vehicle_2024'::'Physical Architecture'::'Physical Functions'::'Root Physical Function'.'Transfer Energy'.'Generate heat'); 
                        ref :>> ownedFunctionalExchanges =  ('eRod_Autonomous_Vehicle_2024 Project'::'eRod_Autonomous_Vehicle_2024'::'Physical Architecture'::'Physical Functions'::'Root Physical Function'.'Transfer Energy'.'cdce9058-efed-4b3d-963c-24c533b1ddf2'); 
                    }  
                    action 'Motor protect' : PhysicalFunction  { 
                        @CapellaID { eid = "e6e8342e-7d7c-4006-a1c0-38b4fce3257a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Detect temperature limit' : PhysicalFunction  { 
                            @CapellaID { eid = "1c3e5b0c-69f7-440c-8812-96ecc5dc0bd7"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 3' : FunctionOutputPort  { 
                                @CapellaID { eid = "baa3d8d1-9120-429f-bd2d-7dec131bdb56"; } 
                                attribute :>> isControl = false; 
                                attribute :>> isControlType = false; 
                                attribute :>> kindOfNode = ObjectNodeKind::Unspecified; 
                                attribute :>> ordering = ObjectNodeOrderingKind::FIFO; 
                                 
                            }  
                            out port 'FOP 2' : FunctionOutputPort  { 
                                @CapellaID { eid = "8ba2cc80-64d3-40f4-a8b3-aafbe01a8c54"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "b65c19ba-c1a6-417f-8b03-5d84775b95f5"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Physical Architecture'::'Physical Functions'::'Root Physical Function'.'Motor protect'.'Detect temperature limit'.'FOP 3',
                            'eRod_Autonomous_Vehicle_2024 Project'::'eRod_Autonomous_Vehicle_2024'::'Physical Architecture'::'Physical Functions'::'Root Physical Function'.'Motor protect'.'Detect temperature limit'.'FOP 2'); 
                            ref :>> inputs =  ('eRod_Autonomous_Vehicle_2024 Project'::'eRod_Autonomous_Vehicle_2024'::'Physical Architecture'::'Physical Functions'::'Root Physical Function'.'Motor protect'.'Detect temperature limit'.'FIP 1'); 
                        }  
                        action 'Reduce power' : PhysicalFunction  { 
                            @CapellaID { eid = "37d66309-af7c-43f0-a366-e1cecd05c480"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "b1bcdd8d-8a03-4442-8dfd-3fa324c176bd"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "fde14bbb-22a0-43cd-82ef-f53379dfb8f4"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Physical Architecture'::'Physical Functions'::'Root Physical Function'.'Motor protect'.'Reduce power'.'FOP 1'); 
                            ref :>> inputs =  ('eRod_Autonomous_Vehicle_2024 Project'::'eRod_Autonomous_Vehicle_2024'::'Physical Architecture'::'Physical Functions'::'Root Physical Function'.'Motor protect'.'Reduce power'.'FIP 1'); 
                        }  
                        action 'Monitor temperature' : PhysicalFunction  { 
                            @CapellaID { eid = "395c14bd-f036-438c-b871-b29b0f7ed9d2"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 2' : FunctionOutputPort  { 
                                @CapellaID { eid = "de296f53-3c45-4d57-9b80-f4edc7fb235e"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "0317eb2e-0f42-4640-806f-a0845a7118c3"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Physical Architecture'::'Physical Functions'::'Root Physical Function'.'Motor protect'.'Monitor temperature'.'FOP 2'); 
                            ref :>> inputs =  ('eRod_Autonomous_Vehicle_2024 Project'::'eRod_Autonomous_Vehicle_2024'::'Physical Architecture'::'Physical Functions'::'Root Physical Function'.'Motor protect'.'Monitor temperature'.'FIP 1'); 
                        }  
                        interface 'c4dd0ad9-1a8c-47e6-952c-e6c0eed9c14f' : FunctionalExchange 
                            connect source ::> 'eRod_Autonomous_Vehicle_2024 Project'::'eRod_Autonomous_Vehicle_2024'::'Physical Architecture'::'Physical Functions'::'Root Physical Function'.'Motor protect'.'Monitor temperature'.'FOP 2'
                            to target ::> 'eRod_Autonomous_Vehicle_2024 Project'::'eRod_Autonomous_Vehicle_2024'::'Physical Architecture'::'Physical Functions'::'Root Physical Function'.'Motor protect'.'Detect temperature limit'.'FIP 1' { 
                            @CapellaID { eid = "c4dd0ad9-1a8c-47e6-952c-e6c0eed9c14f"; } 
                            attribute :>> isMulticast = false; 
                            attribute :>> isMultireceive = false; 
                            attribute :>> kindOfRate = RateKind::Unspecified; 
                            attribute :>> interfaceName = "Temperature"; 
                             
                        }  
                        interface 'db9bf532-3311-4399-a389-6176776af754' : FunctionalExchange 
                            connect source ::> 'eRod_Autonomous_Vehicle_2024 Project'::'eRod_Autonomous_Vehicle_2024'::'Physical Architecture'::'Physical Functions'::'Root Physical Function'.'Motor protect'.'Detect temperature limit'.'FOP 2'
                            to target ::> 'eRod_Autonomous_Vehicle_2024 Project'::'eRod_Autonomous_Vehicle_2024'::'Physical Architecture'::'Physical Functions'::'Root Physical Function'.'Motor protect'.'Reduce power'.'FIP 1' { 
                            @CapellaID { eid = "db9bf532-3311-4399-a389-6176776af754"; } 
                            attribute :>> isMulticast = false; 
                            attribute :>> isMultireceive = false; 
                            attribute :>> kindOfRate = RateKind::Unspecified; 
                            attribute :>> interfaceName = "Signal"; 
                             
                        }  
                         
                        ref :>> ownedFunctions =  ('eRod_Autonomous_Vehicle_2024 Project'::'eRod_Autonomous_Vehicle_2024'::'Physical Architecture'::'Physical Functions'::'Root Physical Function'.'Motor protect'.'Detect temperature limit',
                        'eRod_Autonomous_Vehicle_2024 Project'::'eRod_Autonomous_Vehicle_2024'::'Physical Architecture'::'Physical Functions'::'Root Physical Function'.'Motor protect'.'Reduce power',
                        'eRod_Autonomous_Vehicle_2024 Project'::'eRod_Autonomous_Vehicle_2024'::'Physical Architecture'::'Physical Functions'::'Root Physical Function'.'Motor protect'.'Monitor temperature'); 
                        ref :>> ownedFunctionalExchanges =  ('eRod_Autonomous_Vehicle_2024 Project'::'eRod_Autonomous_Vehicle_2024'::'Physical Architecture'::'Physical Functions'::'Root Physical Function'.'Motor protect'.'c4dd0ad9-1a8c-47e6-952c-e6c0eed9c14f',
                        'eRod_Autonomous_Vehicle_2024 Project'::'eRod_Autonomous_Vehicle_2024'::'Physical Architecture'::'Physical Functions'::'Root Physical Function'.'Motor protect'.'db9bf532-3311-4399-a389-6176776af754'); 
                    }  
                    action 'Controll temperature' : PhysicalFunction  { 
                        @CapellaID { eid = "f8b56107-9696-43ee-ad1b-ee1c40410590"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Limit power' : PhysicalFunction  { 
                            @CapellaID { eid = "adb92edd-55a7-41d6-9bbd-4027b00ff3bd"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 2' : FunctionOutputPort  { 
                                @CapellaID { eid = "6f14e171-b528-4069-828c-e1dd82f88177"; } 
                                attribute :>> isControl = false; 
                                attribute :>> isControlType = false; 
                                attribute :>> kindOfNode = ObjectNodeKind::Unspecified; 
                                attribute :>> ordering = ObjectNodeOrderingKind::FIFO; 
                                 
                            }  
                            in port 'FIP 2' : FunctionInputPort  { 
                                @CapellaID { eid = "656276ae-3040-48ce-8b00-194518c6f79f"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Physical Architecture'::'Physical Functions'::'Root Physical Function'.'Controll temperature'.'Limit power'.'FOP 2'); 
                            ref :>> inputs =  ('eRod_Autonomous_Vehicle_2024 Project'::'eRod_Autonomous_Vehicle_2024'::'Physical Architecture'::'Physical Functions'::'Root Physical Function'.'Controll temperature'.'Limit power'.'FIP 2'); 
                        }  
                         
                        ref :>> ownedFunctions =  ('eRod_Autonomous_Vehicle_2024 Project'::'eRod_Autonomous_Vehicle_2024'::'Physical Architecture'::'Physical Functions'::'Root Physical Function'.'Controll temperature'.'Limit power'); 
                    }  
                    action 'deliver mechanical power' : PhysicalFunction  { 
                        @CapellaID { eid = "2a96efd0-da7b-4b2e-b0ab-cbdb6222fc20"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "85941a20-e524-499b-90b9-c0761db68c1b"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "d8c9f0ca-89e1-4218-b163-c4c94397f2bb"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "e63125bd-b151-4376-8304-a3da38554c1b"; } 
                            attribute :>> isControl = false; 
                            attribute :>> isControlType = false; 
                            attribute :>> kindOfNode = ObjectNodeKind::Unspecified; 
                            attribute :>> ordering = ObjectNodeOrderingKind::FIFO; 
                             
                        }  
                        in port 'FIP 3' : FunctionInputPort  { 
                            @CapellaID { eid = "56a2644c-17bb-4f90-9ba8-c80957aca176"; } 
                            attribute :>> isControl = false; 
                            attribute :>> isControlType = false; 
                            attribute :>> kindOfNode = ObjectNodeKind::Unspecified; 
                            attribute :>> ordering = ObjectNodeOrderingKind::FIFO; 
                             
                        }  
                        in port 'FIP 4' : FunctionInputPort  { 
                            @CapellaID { eid = "93bbf508-c09c-42af-8fd5-667ea7380cd3"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'deliver mechanical power'.'FOP 1',
                        'eRod_Autonomous_Vehicle_2024 Project'::'eRod_Autonomous_Vehicle_2024'::'Physical Architecture'::'Physical Functions'::'Root Physical Function'.'deliver mechanical power'.'FOP 2'); 
                        ref :>> inputs =  ('eRod_Autonomous_Vehicle_2024 Project'::'eRod_Autonomous_Vehicle_2024'::'Physical Architecture'::'Physical Functions'::'Root Physical Function'.'deliver mechanical power'.'FIP 1',
                        'eRod_Autonomous_Vehicle_2024 Project'::'eRod_Autonomous_Vehicle_2024'::'Physical Architecture'::'Physical Functions'::'Root Physical Function'.'deliver mechanical power'.'FIP 3',
                        'eRod_Autonomous_Vehicle_2024 Project'::'eRod_Autonomous_Vehicle_2024'::'Physical Architecture'::'Physical Functions'::'Root Physical Function'.'deliver mechanical power'.'FIP 4'); 
                    }  
                    action 'Generate heat (Rotor)' : PhysicalFunction  { 
                        @CapellaID { eid = "c3807447-f6d0-4050-b1cc-cf4788bd5ccd"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "bd8c7d1c-9cb2-41c7-8037-d0d7cb5e5ecf"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "984133de-74b6-4a0e-835f-beab6f6072fb"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Generate heat (Rotor)'.'FOP 1'); 
                        ref :>> inputs =  ('eRod_Autonomous_Vehicle_2024 Project'::'eRod_Autonomous_Vehicle_2024'::'Physical Architecture'::'Physical Functions'::'Root Physical Function'.'Generate heat (Rotor)'.'FIP 1'); 
                    }  
                    action 'Provide magnetic field' : PhysicalFunction  { 
                        @CapellaID { eid = "e83c7bda-c5eb-4f63-a4b2-ee1b4f60277a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "2322e11e-e11a-4f44-a8da-1790e5ce917f"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "368ebc1e-3fab-4183-b261-dfabf895c027"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Provide magnetic field'.'FOP 1'); 
                        ref :>> inputs =  ('eRod_Autonomous_Vehicle_2024 Project'::'eRod_Autonomous_Vehicle_2024'::'Physical Architecture'::'Physical Functions'::'Root Physical Function'.'Provide magnetic field'.'FIP 1'); 
                    }  
                    action 'Generate Heat (Stator)' : PhysicalFunction  { 
                        @CapellaID { eid = "bdb6c9ef-7bc6-48b4-b2b1-792a9385324d"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "ed97a7f0-ae9f-4f45-997c-64e44b5aa418"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "102230d9-168c-4f78-b50d-ab166fa05319"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Generate Heat (Stator)'.'FOP 1'); 
                        ref :>> inputs =  ('eRod_Autonomous_Vehicle_2024 Project'::'eRod_Autonomous_Vehicle_2024'::'Physical Architecture'::'Physical Functions'::'Root Physical Function'.'Generate Heat (Stator)'.'FIP 1'); 
                    }  
                    action 'protect' : PhysicalFunction  { 
                        @CapellaID { eid = "6e4e3e97-c430-4c80-b338-3f04289c8761"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                         
                    }  
                    action 'Transfer heat' : PhysicalFunction  { 
                        @CapellaID { eid = "278aff21-d68c-4110-a129-dbc5e82aa417"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "5737448d-e57a-4c85-b707-a89043b9c784"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "f359aead-442d-421f-bdaf-2f91aa616f0d"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Transfer heat'.'FOP 1'); 
                        ref :>> inputs =  ('eRod_Autonomous_Vehicle_2024 Project'::'eRod_Autonomous_Vehicle_2024'::'Physical Architecture'::'Physical Functions'::'Root Physical Function'.'Transfer heat'.'FIP 1'); 
                    }  
                    action 'Gather 21' : PhysicalFunction  { 
                        @CapellaID { eid = "b348b9fe-9aed-497e-96a4-095807fa8ca8"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::GATHER; 
                        attribute :>> isMaxInclusive = false; 
                        attribute :>> isMinInclusive = false; 
                        attribute :>> isOrdered = false; 
                        attribute :>> isUnique = false; 
                        out port 'FOP 1' : FunctionOutputPort  { 
                            @CapellaID { eid = "a79a7c64-0e4c-43c1-aeb5-f2785f54e1c3"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "357fa6ca-a05b-4040-a854-f3681738103c"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "cc6afda9-f944-4303-96cd-7caf67cf5b97"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Gather 21'.'FOP 1'); 
                        ref :>> inputs =  ('eRod_Autonomous_Vehicle_2024 Project'::'eRod_Autonomous_Vehicle_2024'::'Physical Architecture'::'Physical Functions'::'Root Physical Function'.'Gather 21'.'FIP 1',
                        'eRod_Autonomous_Vehicle_2024 Project'::'eRod_Autonomous_Vehicle_2024'::'Physical Architecture'::'Physical Functions'::'Root Physical Function'.'Gather 21'.'FIP 2'); 
                    }  
                    action 'Motor Start' : PhysicalFunction  { 
                        @CapellaID { eid = "96853eb8-4a28-4cd0-bd3f-d0e49ba53081"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outCause' : FunctionOutputPort  { 
                            @CapellaID { eid = "f564b0b6-fcbc-4b01-b61d-e5efcd039eb6"; } 
                            attribute :>> isControl = false; 
                            attribute :>> isControlType = false; 
                            attribute :>> kindOfNode = ObjectNodeKind::Unspecified; 
                            attribute :>> ordering = ObjectNodeOrderingKind::FIFO; 
                             
                        }  
                        in port 'FIP 2' : FunctionInputPort  { 
                            @CapellaID { eid = "5e0cc179-9d97-432f-8f5e-8c9627ec4a76"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Motor Start'.'outCause'); 
                        ref :>> inputs =  ('eRod_Autonomous_Vehicle_2024 Project'::'eRod_Autonomous_Vehicle_2024'::'Physical Architecture'::'Physical Functions'::'Root Physical Function'.'Motor Start'.'FIP 2'); 
                    }  
                    action 'Transfer power to Axies' : PhysicalFunction  { 
                        @CapellaID { eid = "f8798cff-eb39-4143-a6a1-78c010b82da9"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "3c90af61-1b9b-46bb-bcce-f07cc65d0093"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "607c7d18-95a9-4382-8f5e-1904c064aef6"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Transfer power to Axies'.'FOP 1'); 
                        ref :>> inputs =  ('eRod_Autonomous_Vehicle_2024 Project'::'eRod_Autonomous_Vehicle_2024'::'Physical Architecture'::'Physical Functions'::'Root Physical Function'.'Transfer power to Axies'.'FIP 1'); 
                    }  
                    action 'Apply rotation on wheels' : PhysicalFunction  { 
                        @CapellaID { eid = "b02de6ff-4e23-473e-8762-c62bef6c12bb"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 2' : FunctionOutputPort  { 
                            @CapellaID { eid = "2dadd0d8-7ea0-41cf-888c-55fedecb0c43"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "96b2bea2-c50b-43e8-8298-5df957e7cad8"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Apply rotation on wheels'.'FOP 2'); 
                        ref :>> inputs =  ('eRod_Autonomous_Vehicle_2024 Project'::'eRod_Autonomous_Vehicle_2024'::'Physical Architecture'::'Physical Functions'::'Root Physical Function'.'Apply rotation on wheels'.'FIP 1'); 
                    }  
                    action 'Split 25' : PhysicalFunction  { 
                        @CapellaID { eid = "0faa31f2-b215-4216-af42-5c16e06e862b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::SPLIT; 
                        attribute :>> isMaxInclusive = false; 
                        attribute :>> isMinInclusive = false; 
                        attribute :>> isOrdered = false; 
                        attribute :>> isUnique = false; 
                        out port 'FOP 1' : FunctionOutputPort  { 
                            @CapellaID { eid = "8754a9a4-3917-4820-b253-74184d12f2f8"; } 
                            attribute :>> isControl = false; 
                            attribute :>> isControlType = false; 
                            attribute :>> kindOfNode = ObjectNodeKind::Unspecified; 
                            attribute :>> ordering = ObjectNodeOrderingKind::FIFO; 
                             
                        }  
                        out port 'FOP 2' : FunctionOutputPort  { 
                            @CapellaID { eid = "ba76f7ef-10bc-452e-b858-663a50083cc7"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "9724e352-098d-42d2-9f4c-320f49ffdb88"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Split 25'.'FOP 1',
                        'eRod_Autonomous_Vehicle_2024 Project'::'eRod_Autonomous_Vehicle_2024'::'Physical Architecture'::'Physical Functions'::'Root Physical Function'.'Split 25'.'FOP 2'); 
                        ref :>> inputs =  ('eRod_Autonomous_Vehicle_2024 Project'::'eRod_Autonomous_Vehicle_2024'::'Physical Architecture'::'Physical Functions'::'Root Physical Function'.'Split 25'.'FIP 1'); 
                    }  
                    action 'Improve motor performance' : PhysicalFunction  { 
                        @CapellaID { eid = "e3569349-7b56-49af-9d45-f5c0341c9b11"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "6e25e1b4-2d2e-4c90-aaf3-c55617e019ad"; } 
                            attribute :>> isControl = false; 
                            attribute :>> isControlType = false; 
                            attribute :>> kindOfNode = ObjectNodeKind::Unspecified; 
                            attribute :>> ordering = ObjectNodeOrderingKind::FIFO; 
                             
                        }  
                        in port 'FIP 1' : FunctionInputPort  { 
                            @CapellaID { eid = "95ef72f2-c8c2-4650-bb32-b59bdc09bc1b"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Improve motor performance'.'FOP 1'); 
                        ref :>> inputs =  ('eRod_Autonomous_Vehicle_2024 Project'::'eRod_Autonomous_Vehicle_2024'::'Physical Architecture'::'Physical Functions'::'Root Physical Function'.'Improve motor performance'.'FIP 1'); 
                    }  
                    action 'remote update' : PhysicalFunction  { 
                        @CapellaID { eid = "101bd3bb-ae45-4ebf-bab1-345aed4c26e1"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "b112d10f-4623-47a6-8cc3-7a709b71fc43"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Physical Architecture'::'Physical Functions'::'Root Physical Function'.'remote update'.'FIP 1'); 
                    }  
                    action 'connected to the center' : PhysicalFunction  { 
                        @CapellaID { eid = "816769a2-e2bf-4675-b7be-c3c59a850f78"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "957a248c-d138-42d5-9be4-6291b27b8fc0"; } 
                            attribute :>> isControl = false; 
                            attribute :>> isControlType = false; 
                            attribute :>> kindOfNode = ObjectNodeKind::Unspecified; 
                            attribute :>> ordering = ObjectNodeOrderingKind::FIFO; 
                             
                        }  
                        in port 'inApproval' : FunctionInputPort  { 
                            @CapellaID { eid = "ea472220-a558-487c-af3e-fc75c77ef90b"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'connected to the center'.'FOP 1'); 
                        ref :>> inputs =  ('eRod_Autonomous_Vehicle_2024 Project'::'eRod_Autonomous_Vehicle_2024'::'Physical Architecture'::'Physical Functions'::'Root Physical Function'.'connected to the center'.'inApproval'); 
                    }  
                    action 'Provide electrical energy' : PhysicalFunction  { 
                        @CapellaID { eid = "46824c28-37c0-42c8-828f-c7c8ddb05897"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "ebb47053-a272-4711-83d5-319766d967df"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Provide electrical energy'.'FOP 1'); 
                    }  
                    action 'Pull drift compensation (PDC)' : PhysicalFunction  { 
                        @CapellaID { eid = "d32cdabb-2e78-42b3-b1e6-bf5aae4027cd"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Active nibble compensation (ANC)' : PhysicalFunction  { 
                        @CapellaID { eid = "a7b535c2-45df-44c0-a737-37a6b524af2c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Arbiter/limiter (A/L)' : PhysicalFunction  { 
                        @CapellaID { eid = "2f217175-271e-4383-9c2a-c1014517b97b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Steer Feel (SF)' : PhysicalFunction  { 
                        @CapellaID { eid = "19758cc9-3f86-4036-aea2-7723fb8f4747"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Prevent accent' : PhysicalFunction  { 
                        @CapellaID { eid = "e1f23021-547e-46d7-825e-48e7e3b782c3"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Detect Objects' : PhysicalFunction  { 
                        @CapellaID { eid = "77402269-83a9-4900-a12b-41518e33e13a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                    }  
                    action 'Provide solution' : PhysicalFunction  { 
                        @CapellaID { eid = "de6bdff3-e5cb-4f0e-aaf5-787d782c6213"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 2' : FunctionOutputPort  { 
                            @CapellaID { eid = "2d80a007-66e0-4d7c-b2a3-435998b26158"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Provide solution'.'FOP 2'); 
                    }  
                    action 'Slow down and stop the vehicle' : PhysicalFunction  { 
                        @CapellaID { eid = "e4a88a93-3363-4aa5-8a1d-d6c3ed972816"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Brake' : PhysicalFunction  { 
                            @CapellaID { eid = "0848a700-da3c-49b0-b6fe-1ec64f114fab"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            in port 'FIP 1' : FunctionInputPort  { 
                                @CapellaID { eid = "7a7b4187-ee9a-4502-acf5-91ec941495c4"; } 
                                attribute :>> isControl = false; 
                                attribute :>> isControlType = false; 
                                attribute :>> kindOfNode = ObjectNodeKind::Unspecified; 
                                attribute :>> ordering = ObjectNodeOrderingKind::FIFO; 
                                 
                            }  
                             
                            ref :>> inputs =  ('eRod_Autonomous_Vehicle_2024 Project'::'eRod_Autonomous_Vehicle_2024'::'Physical Architecture'::'Physical Functions'::'Root Physical Function'.'Slow down and stop the vehicle'.'Brake'.'FIP 1'); 
                        }  
                         
                        ref :>> ownedFunctions =  ('eRod_Autonomous_Vehicle_2024 Project'::'eRod_Autonomous_Vehicle_2024'::'Physical Architecture'::'Physical Functions'::'Root Physical Function'.'Slow down and stop the vehicle'.'Brake'); 
                    }  
                    action 'Plan path' : PhysicalFunction  { 
                        @CapellaID { eid = "e6c2cae8-c636-491b-bbeb-0cd68f7ee637"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                         
                    }  
                    action 'Drive route' : PhysicalFunction  { 
                        @CapellaID { eid = "467f9919-d21a-49c3-9d40-4a10f71d9ecf"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "c5ab7707-5f30-4e7e-8e43-2491b30192ed"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Drive route'.'FOP 1'); 
                    }  
                    action 'Reflect lights' : PhysicalFunction  { 
                        @CapellaID { eid = "f5c18e9e-8e17-4a86-a242-da45e87e7956"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'Reflect Light FOP 1' : FunctionOutputPort  { 
                            @CapellaID { eid = "d38e22fa-44bc-4066-9c11-9d156a6e1650"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Reflect lights'.'Reflect Light FOP 1'); 
                    }  
                    action 'Steer Wheels' : PhysicalFunction  { 
                        @CapellaID { eid = "43c64d51-b345-40a6-981c-450dfcd9fa61"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "e6eeebde-6a77-44d8-9bf3-22e04d102a7b"; } 
                            attribute :>> isControl = false; 
                            attribute :>> isControlType = false; 
                            attribute :>> kindOfNode = ObjectNodeKind::Unspecified; 
                            attribute :>> ordering = ObjectNodeOrderingKind::FIFO; 
                             
                        }  
                        action 'Measure steering angle' : PhysicalFunction  { 
                            @CapellaID { eid = "e3cea3bf-866d-4c8b-bc9d-5cd3d42af985"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "0c60f492-a7ae-4638-aa98-a4ce019dc40b"; } 
                                attribute :>> isControl = false; 
                                attribute :>> isControlType = false; 
                                attribute :>> kindOfNode = ObjectNodeKind::Unspecified; 
                                attribute :>> ordering = ObjectNodeOrderingKind::FIFO; 
                                ref :>> outgoingExchangeItems =  ('eRod_Autonomous_Vehicle_2024 Project'::'eRod_Autonomous_Vehicle_2024'::'Physical Architecture'::'Data'::'Steering Angle'); 
                            }  
                            in port 'FIP 1' : FunctionInputPort  { 
                                @CapellaID { eid = "f380e401-b20e-4a17-800f-3111b204c714"; } 
                                attribute :>> isControl = false; 
                                attribute :>> isControlType = false; 
                                attribute :>> kindOfNode = ObjectNodeKind::Unspecified; 
                                attribute :>> ordering = ObjectNodeOrderingKind::FIFO; 
                                ref :>> incomingExchangeItems =  ('eRod_Autonomous_Vehicle_2024 Project'::'eRod_Autonomous_Vehicle_2024'::'Physical Architecture'::'Data'::'Steering Angle'); 
                                 
                            }  
                            ref :>> outputs =  ('eRod_Autonomous_Vehicle_2024 Project'::'eRod_Autonomous_Vehicle_2024'::'Physical Architecture'::'Physical Functions'::'Root Physical Function'.'Steer Wheels'.'Measure steering angle'.'FOP 1'); 
                            ref :>> inputs =  ('eRod_Autonomous_Vehicle_2024 Project'::'eRod_Autonomous_Vehicle_2024'::'Physical Architecture'::'Physical Functions'::'Root Physical Function'.'Steer Wheels'.'Measure steering angle'.'FIP 1'); 
                        }  
                        action 'Measure steering force' : PhysicalFunction  { 
                            @CapellaID { eid = "343e633e-454d-433d-adc3-72f41666a29f"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "277e0fb8-53f9-4e1e-8497-51260e0cac17"; } 
                                attribute :>> isControl = false; 
                                attribute :>> isControlType = false; 
                                attribute :>> kindOfNode = ObjectNodeKind::Unspecified; 
                                attribute :>> ordering = ObjectNodeOrderingKind::FIFO; 
                                ref :>> outgoingExchangeItems =  ('eRod_Autonomous_Vehicle_2024 Project'::'eRod_Autonomous_Vehicle_2024'::'Physical Architecture'::'Data'::'Steering Force'); 
                            }  
                            in port 'FIP 1' : FunctionInputPort  { 
                                @CapellaID { eid = "35f54b86-9c26-4feb-a429-fd536febe675"; } 
                                attribute :>> isControl = false; 
                                attribute :>> isControlType = false; 
                                attribute :>> kindOfNode = ObjectNodeKind::Unspecified; 
                                attribute :>> ordering = ObjectNodeOrderingKind::FIFO; 
                                ref :>> incomingExchangeItems =  ('eRod_Autonomous_Vehicle_2024 Project'::'eRod_Autonomous_Vehicle_2024'::'Physical Architecture'::'Data'::'Steering Force'); 
                            }  
                            ref :>> outputs =  ('eRod_Autonomous_Vehicle_2024 Project'::'eRod_Autonomous_Vehicle_2024'::'Physical Architecture'::'Physical Functions'::'Root Physical Function'.'Steer Wheels'.'Measure steering force'.'FOP 1'); 
                            ref :>> inputs =  ('eRod_Autonomous_Vehicle_2024 Project'::'eRod_Autonomous_Vehicle_2024'::'Physical Architecture'::'Physical Functions'::'Root Physical Function'.'Steer Wheels'.'Measure steering force'.'FIP 1'); 
                        }  
                        action 'Automatic Steering' : PhysicalFunction  { 
                            @CapellaID { eid = "f1e1d249-8780-4621-855e-bbba894b5fb5"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "0c32a474-6f40-4b7f-babf-b8ccc3b78e10"; } 
                                attribute :>> isControl = false; 
                                attribute :>> isControlType = false; 
                                attribute :>> kindOfNode = ObjectNodeKind::Unspecified; 
                                attribute :>> ordering = ObjectNodeOrderingKind::FIFO; 
                                 
                            }  
                            out port 'FOP 2' : FunctionOutputPort  { 
                                @CapellaID { eid = "349604cf-1e29-4cbe-9619-b6c17228ca75"; } 
                                attribute :>> isControl = false; 
                                attribute :>> isControlType = false; 
                                attribute :>> kindOfNode = ObjectNodeKind::Unspecified; 
                                attribute :>> ordering = ObjectNodeOrderingKind::FIFO; 
                            }  
                            in port 'FIP 2' : FunctionInputPort  { 
                                @CapellaID { eid = "0dae8a8f-0728-4786-96c5-3bb0bcc8b479"; } 
                                attribute :>> isControl = false; 
                                attribute :>> isControlType = false; 
                                attribute :>> kindOfNode = ObjectNodeKind::Unspecified; 
                                attribute :>> ordering = ObjectNodeOrderingKind::FIFO; 
                                 
                            }  
                            in port 'St Cmds' : FunctionInputPort  { 
                                @CapellaID { eid = "805684a6-ee7f-4241-9606-6f7685823c87"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "0ebae41a-255b-49ff-b321-2b5c90f781ff"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Physical Architecture'::'Physical Functions'::'Root Physical Function'.'Steer Wheels'.'Automatic Steering'.'FOP 1',
                            'eRod_Autonomous_Vehicle_2024 Project'::'eRod_Autonomous_Vehicle_2024'::'Physical Architecture'::'Physical Functions'::'Root Physical Function'.'Steer Wheels'.'Automatic Steering'.'FOP 2'); 
                            ref :>> inputs =  ('eRod_Autonomous_Vehicle_2024 Project'::'eRod_Autonomous_Vehicle_2024'::'Physical Architecture'::'Physical Functions'::'Root Physical Function'.'Steer Wheels'.'Automatic Steering'.'FIP 2',
                            'eRod_Autonomous_Vehicle_2024 Project'::'eRod_Autonomous_Vehicle_2024'::'Physical Architecture'::'Physical Functions'::'Root Physical Function'.'Steer Wheels'.'Automatic Steering'.'St Cmds',
                            'eRod_Autonomous_Vehicle_2024 Project'::'eRod_Autonomous_Vehicle_2024'::'Physical Architecture'::'Physical Functions'::'Root Physical Function'.'Steer Wheels'.'Automatic Steering'.'FIP 1'); 
                        }  
                        action 'Assist steering' : PhysicalFunction  { 
                            @CapellaID { eid = "252b7b9c-5d0b-47f6-b36c-818034e47828"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 2' : FunctionOutputPort  { 
                                @CapellaID { eid = "e926e587-bd14-4615-b99f-28f2de003eb8"; } 
                                attribute :>> isControl = false; 
                                attribute :>> isControlType = false; 
                                attribute :>> kindOfNode = ObjectNodeKind::Unspecified; 
                                attribute :>> ordering = ObjectNodeOrderingKind::FIFO; 
                            }  
                            out port 'FOP 4' : FunctionOutputPort  { 
                                @CapellaID { eid = "392d267b-a310-4731-bec5-ab7b3d201507"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "701f4895-e8f9-4dce-a800-04468f36a6e2"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'Physical Architecture'::'Physical Functions'::'Root Physical Function'.'Steer Wheels'.'Assist steering'.'FOP 2',
                            'eRod_Autonomous_Vehicle_2024 Project'::'eRod_Autonomous_Vehicle_2024'::'Physical Architecture'::'Physical Functions'::'Root Physical Function'.'Steer Wheels'.'Assist steering'.'FOP 4'); 
                            ref :>> inputs =  ('eRod_Autonomous_Vehicle_2024 Project'::'eRod_Autonomous_Vehicle_2024'::'Physical Architecture'::'Physical Functions'::'Root Physical Function'.'Steer Wheels'.'Assist steering'.'FIP 1'); 
                        }  
                        action 'Torque steer compensation (TSC)' : PhysicalFunction  { 
                            @CapellaID { eid = "5ae5b27b-95a1-4c22-b865-15c9b34ff055"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "657d9d65-ebf4-4916-a20c-31309a7a9897"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "546a3a5f-421f-4426-8509-23eabad8f83c"; } 
                                attribute :>> isControl = false; 
                                attribute :>> isControlType = false; 
                                attribute :>> kindOfNode = ObjectNodeKind::Unspecified; 
                                attribute :>> ordering = ObjectNodeOrderingKind::FIFO; 
                                ref :>> incomingExchangeItems =  ('eRod_Autonomous_Vehicle_2024 Project'::'eRod_Autonomous_Vehicle_2024'::'Physical Architecture'::'Data'::'Steering Force'); 
                            }  
                            in port 'FIP 2' : FunctionInputPort  { 
                                @CapellaID { eid = "79771cd1-0e6f-4508-8d0d-96da0686ebfe"; } 
                                attribute :>> isControl = false; 
                                attribute :>> isControlType = false; 
                                attribute :>> kindOfNode = ObjectNodeKind::Unspecified; 
                                attribute :>> ordering = ObjectNodeOrderingKind::FIFO; 
                            }  
                            in port 'FIP 3' : FunctionInputPort  { 
                                @CapellaID { eid = "8e85c861-6d0b-42be-bfe3-95585c73d21f"; } 
                                attribute :>> isControl = false; 
                                attribute :>> isControlType = false; 
                                attribute :>> kindOfNode = ObjectNodeKind::Unspecified; 
                                attribute :>> ordering = ObjectNodeOrderingKind::FIFO; 
                                ref :>> incomingExchangeItems =  ('eRod_Autonomous_Vehicle_2024 Project'::'eRod_Autonomous_Vehicle_2024'::'Physical Architecture'::'Data'::'Steering Angle'); 
                            }  
                            ref :>> outputs =  ('eRod_Autonomous_Vehicle_2024 Project'::'eRod_Autonomous_Vehicle_2024'::'Physical Architecture'::'Physical Functions'::'Root Physical Function'.'Steer Wheels'.'Torque steer compensation (TSC)'.'FOP 1'); 
                            ref :>> inputs =  ('eRod_Autonomous_Vehicle_2024 Project'::'eRod_Autonomous_Vehicle_2024'::'Physical Architecture'::'Physical Functions'::'Root Physical Function'.'Steer Wheels'.'Torque steer compensation (TSC)'.'FIP 1',
                            'eRod_Autonomous_Vehicle_2024 Project'::'eRod_Autonomous_Vehicle_2024'::'Physical Architecture'::'Physical Functions'::'Root Physical Function'.'Steer Wheels'.'Torque steer compensation (TSC)'.'FIP 2',
                            'eRod_Autonomous_Vehicle_2024 Project'::'eRod_Autonomous_Vehicle_2024'::'Physical Architecture'::'Physical Functions'::'Root Physical Function'.'Steer Wheels'.'Torque steer compensation (TSC)'.'FIP 3'); 
                        }  
                        action 'Force to Road Left Front' : PhysicalFunction  { 
                            @CapellaID { eid = "f8232f9f-6e59-4c9b-a20b-8fe5ca2af0e3"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "96540dc9-7174-4c3d-84d6-28f2730f85b9"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "3d764d16-c3dc-4306-9a8a-96082c21382d"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'Physical Architecture'::'Physical Functions'::'Root Physical Function'.'Steer Wheels'.'Force to Road Left Front'.'FOP 1'); 
                            ref :>> inputs =  ('eRod_Autonomous_Vehicle_2024 Project'::'eRod_Autonomous_Vehicle_2024'::'Physical Architecture'::'Physical Functions'::'Root Physical Function'.'Steer Wheels'.'Force to Road Left Front'.'FIP 1'); 
                        }  
                        action 'Force to Road Right Front' : PhysicalFunction  { 
                            @CapellaID { eid = "7f131643-ad32-4094-bda4-39d9d02922ac"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "d36f1814-938c-4acf-a670-634b6c0de874"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "1f72f725-519c-4e0d-ba30-2e23a4be7cd7"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'Physical Architecture'::'Physical Functions'::'Root Physical Function'.'Steer Wheels'.'Force to Road Right Front'.'FOP 1'); 
                            ref :>> inputs =  ('eRod_Autonomous_Vehicle_2024 Project'::'eRod_Autonomous_Vehicle_2024'::'Physical Architecture'::'Physical Functions'::'Root Physical Function'.'Steer Wheels'.'Force to Road Right Front'.'FIP 1'); 
                        }  
                        action 'Transmit Left Force' : PhysicalFunction  { 
                            @CapellaID { eid = "9fdcf14d-5042-415a-be99-7a85cd737e91"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "c69bf0db-3250-48e1-8268-73e717fdaf9c"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "d5fbcc3f-caa5-47e3-be9a-029c77ac3d79"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'Physical Architecture'::'Physical Functions'::'Root Physical Function'.'Steer Wheels'.'Transmit Left Force'.'FOP 1'); 
                            ref :>> inputs =  ('eRod_Autonomous_Vehicle_2024 Project'::'eRod_Autonomous_Vehicle_2024'::'Physical Architecture'::'Physical Functions'::'Root Physical Function'.'Steer Wheels'.'Transmit Left Force'.'FIP 1'); 
                        }  
                        action 'Transmit Right Force' : PhysicalFunction  { 
                            @CapellaID { eid = "b9cee805-ee21-4678-80e4-c24e83bc9059"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 3' : FunctionOutputPort  { 
                                @CapellaID { eid = "ec858ee6-0714-4f72-a08a-0f4a53541753"; } 
                                attribute :>> isControl = false; 
                                attribute :>> isControlType = false; 
                                attribute :>> kindOfNode = ObjectNodeKind::Unspecified; 
                                attribute :>> ordering = ObjectNodeOrderingKind::FIFO; 
                            }  
                            in port 'FIP 1' : FunctionInputPort  { 
                                @CapellaID { eid = "a67f27ac-7fe8-4e3a-bbac-8f63a77ee296"; } 
                                attribute :>> isControl = false; 
                                attribute :>> isControlType = false; 
                                attribute :>> kindOfNode = ObjectNodeKind::Unspecified; 
                                attribute :>> ordering = ObjectNodeOrderingKind::FIFO; 
                            }  
                            ref :>> outputs =  ('eRod_Autonomous_Vehicle_2024 Project'::'eRod_Autonomous_Vehicle_2024'::'Physical Architecture'::'Physical Functions'::'Root Physical Function'.'Steer Wheels'.'Transmit Right Force'.'FOP 3'); 
                            ref :>> inputs =  ('eRod_Autonomous_Vehicle_2024 Project'::'eRod_Autonomous_Vehicle_2024'::'Physical Architecture'::'Physical Functions'::'Root Physical Function'.'Steer Wheels'.'Transmit Right Force'.'FIP 1'); 
                        }  
                        interface '4d8fe037-1771-406b-8cb4-b33ea24a9b44' : FunctionalExchange 
                            connect source ::> 'eRod_Autonomous_Vehicle_2024 Project'::'eRod_Autonomous_Vehicle_2024'::'Physical Architecture'::'Physical Functions'::'Root Physical Function'.'Steer Wheels'.'Automatic Steering'.'FOP 2'
                            to target ::> 'eRod_Autonomous_Vehicle_2024 Project'::'eRod_Autonomous_Vehicle_2024'::'Physical Architecture'::'Physical Functions'::'Root Physical Function'.'Steer Wheels'.'Torque steer compensation (TSC)'.'FIP 2' { 
                            @CapellaID { eid = "4d8fe037-1771-406b-8cb4-b33ea24a9b44"; } 
                            attribute :>> isMulticast = false; 
                            attribute :>> isMultireceive = false; 
                            attribute :>> kindOfRate = RateKind::Unspecified; 
                            attribute :>> interfaceName = "Steer Command"; 
                        }  
                        interface '73d30128-b552-4b75-a646-c889356202be' : FunctionalExchange 
                            connect source ::> 'eRod_Autonomous_Vehicle_2024 Project'::'eRod_Autonomous_Vehicle_2024'::'Physical Architecture'::'Physical Functions'::'Root Physical Function'.'Steer Wheels'.'Measure steering angle'.'FOP 1'
                            to target ::> 'eRod_Autonomous_Vehicle_2024 Project'::'eRod_Autonomous_Vehicle_2024'::'Physical Architecture'::'Physical Functions'::'Root Physical Function'.'Steer Wheels'.'Torque steer compensation (TSC)'.'FIP 3' { 
                            @CapellaID { eid = "73d30128-b552-4b75-a646-c889356202be"; } 
                            attribute :>> isMulticast = false; 
                            attribute :>> isMultireceive = false; 
                            attribute :>> kindOfRate = RateKind::Unspecified; 
                            attribute :>> interfaceName = "Steering Angle"; 
                            ref :>> exchangedItems =  ('eRod_Autonomous_Vehicle_2024 Project'::'eRod_Autonomous_Vehicle_2024'::'Physical Architecture'::'Data'::'Steering Angle'); 
                        }  
                        interface '2a944e7a-8965-4971-870b-df89fc55c7dd' : FunctionalExchange 
                            connect source ::> 'eRod_Autonomous_Vehicle_2024 Project'::'eRod_Autonomous_Vehicle_2024'::'Physical Architecture'::'Physical Functions'::'Root Physical Function'.'Steer Wheels'.'Assist steering'.'FOP 2'
                            to target ::> 'eRod_Autonomous_Vehicle_2024 Project'::'eRod_Autonomous_Vehicle_2024'::'Physical Architecture'::'Physical Functions'::'Root Physical Function'.'Steer Wheels'.'Transmit Left Force'.'FIP 1' { 
                            @CapellaID { eid = "2a944e7a-8965-4971-870b-df89fc55c7dd"; } 
                            attribute :>> isMulticast = false; 
                            attribute :>> isMultireceive = false; 
                            attribute :>> kindOfRate = RateKind::Unspecified; 
                            attribute :>> interfaceName = "Force to Knuckle"; 
                        }  
                        interface 'a9b2c213-d86e-4c47-a6f3-8f6216ccdb49' : FunctionalExchange 
                            connect source ::> 'eRod_Autonomous_Vehicle_2024 Project'::'eRod_Autonomous_Vehicle_2024'::'Physical Architecture'::'Physical Functions'::'Root Physical Function'.'Steer Wheels'.'Transmit Right Force'.'FOP 3'
                            to target ::> 'eRod_Autonomous_Vehicle_2024 Project'::'eRod_Autonomous_Vehicle_2024'::'Physical Architecture'::'Physical Functions'::'Root Physical Function'.'Steer Wheels'.'Force to Road Right Front'.'FIP 1' { 
                            @CapellaID { eid = "a9b2c213-d86e-4c47-a6f3-8f6216ccdb49"; } 
                            attribute :>> isMulticast = false; 
                            attribute :>> isMultireceive = false; 
                            attribute :>> kindOfRate = RateKind::Unspecified; 
                            attribute :>> interfaceName = "FunctionalExchange 4"; 
                        }  
                        interface '872387bc-c61f-4975-bf12-dd220518b44d' : FunctionalExchange 
                            connect source ::> 'eRod_Autonomous_Vehicle_2024 Project'::'eRod_Autonomous_Vehicle_2024'::'Physical Architecture'::'Physical Functions'::'Root Physical Function'.'Steer Wheels'.'Assist steering'.'FOP 4'
                            to target ::> 'eRod_Autonomous_Vehicle_2024 Project'::'eRod_Autonomous_Vehicle_2024'::'Physical Architecture'::'Physical Functions'::'Root Physical Function'.'Steer Wheels'.'Transmit Right Force'.'FIP 1' { 
                            @CapellaID { eid = "872387bc-c61f-4975-bf12-dd220518b44d"; } 
                            attribute :>> isMulticast = false; 
                            attribute :>> isMultireceive = false; 
                            attribute :>> kindOfRate = RateKind::Unspecified; 
                            attribute :>> interfaceName = "Force to Knucle"; 
                        }  
                        interface '4ab23e81-867a-4e42-b992-a665c9ce5324' : FunctionalExchange 
                            connect source ::> 'eRod_Autonomous_Vehicle_2024 Project'::'eRod_Autonomous_Vehicle_2024'::'Physical Architecture'::'Physical Functions'::'Root Physical Function'.'Steer Wheels'.'Transmit Left Force'.'FOP 1'
                            to target ::> 'eRod_Autonomous_Vehicle_2024 Project'::'eRod_Autonomous_Vehicle_2024'::'Physical Architecture'::'Physical Functions'::'Root Physical Function'.'Steer Wheels'.'Force to Road Left Front'.'FIP 1' { 
                            @CapellaID { eid = "4ab23e81-867a-4e42-b992-a665c9ce5324"; } 
                            attribute :>> isMulticast = false; 
                            attribute :>> isMultireceive = false; 
                            attribute :>> kindOfRate = RateKind::Unspecified; 
                            attribute :>> interfaceName = "FunctionalExchange 6"; 
                        }  
                         
                        ref :>> inputs =  ('eRod_Autonomous_Vehicle_2024 Project'::'eRod_Autonomous_Vehicle_2024'::'Physical Architecture'::'Physical Functions'::'Root Physical Function'.'Steer Wheels'.'FIP 1'); 
                        ref :>> ownedFunctions =  ('eRod_Autonomous_Vehicle_2024 Project'::'eRod_Autonomous_Vehicle_2024'::'Physical Architecture'::'Physical Functions'::'Root Physical Function'.'Steer Wheels'.'Measure steering angle',
                        'eRod_Autonomous_Vehicle_2024 Project'::'eRod_Autonomous_Vehicle_2024'::'Physical Architecture'::'Physical Functions'::'Root Physical Function'.'Steer Wheels'.'Measure steering force',
                        'eRod_Autonomous_Vehicle_2024 Project'::'eRod_Autonomous_Vehicle_2024'::'Physical Architecture'::'Physical Functions'::'Root Physical Function'.'Steer Wheels'.'Automatic Steering',
                        'eRod_Autonomous_Vehicle_2024 Project'::'eRod_Autonomous_Vehicle_2024'::'Physical Architecture'::'Physical Functions'::'Root Physical Function'.'Steer Wheels'.'Assist steering',
                        'eRod_Autonomous_Vehicle_2024 Project'::'eRod_Autonomous_Vehicle_2024'::'Physical Architecture'::'Physical Functions'::'Root Physical Function'.'Steer Wheels'.'Torque steer compensation (TSC)',
                        'eRod_Autonomous_Vehicle_2024 Project'::'eRod_Autonomous_Vehicle_2024'::'Physical Architecture'::'Physical Functions'::'Root Physical Function'.'Steer Wheels'.'Force to Road Left Front',
                        'eRod_Autonomous_Vehicle_2024 Project'::'eRod_Autonomous_Vehicle_2024'::'Physical Architecture'::'Physical Functions'::'Root Physical Function'.'Steer Wheels'.'Force to Road Right Front',
                        'eRod_Autonomous_Vehicle_2024 Project'::'eRod_Autonomous_Vehicle_2024'::'Physical Architecture'::'Physical Functions'::'Root Physical Function'.'Steer Wheels'.'Transmit Left Force',
                        'eRod_Autonomous_Vehicle_2024 Project'::'eRod_Autonomous_Vehicle_2024'::'Physical Architecture'::'Physical Functions'::'Root Physical Function'.'Steer Wheels'.'Transmit Right Force'); 
                        ref :>> ownedFunctionalExchanges =  ('eRod_Autonomous_Vehicle_2024 Project'::'eRod_Autonomous_Vehicle_2024'::'Physical Architecture'::'Physical Functions'::'Root Physical Function'.'Steer Wheels'.'4d8fe037-1771-406b-8cb4-b33ea24a9b44',
                        'eRod_Autonomous_Vehicle_2024 Project'::'eRod_Autonomous_Vehicle_2024'::'Physical Architecture'::'Physical Functions'::'Root Physical Function'.'Steer Wheels'.'73d30128-b552-4b75-a646-c889356202be',
                        'eRod_Autonomous_Vehicle_2024 Project'::'eRod_Autonomous_Vehicle_2024'::'Physical Architecture'::'Physical Functions'::'Root Physical Function'.'Steer Wheels'.'2a944e7a-8965-4971-870b-df89fc55c7dd',
                        'eRod_Autonomous_Vehicle_2024 Project'::'eRod_Autonomous_Vehicle_2024'::'Physical Architecture'::'Physical Functions'::'Root Physical Function'.'Steer Wheels'.'a9b2c213-d86e-4c47-a6f3-8f6216ccdb49',
                        'eRod_Autonomous_Vehicle_2024 Project'::'eRod_Autonomous_Vehicle_2024'::'Physical Architecture'::'Physical Functions'::'Root Physical Function'.'Steer Wheels'.'872387bc-c61f-4975-bf12-dd220518b44d',
                        'eRod_Autonomous_Vehicle_2024 Project'::'eRod_Autonomous_Vehicle_2024'::'Physical Architecture'::'Physical Functions'::'Root Physical Function'.'Steer Wheels'.'4ab23e81-867a-4e42-b992-a665c9ce5324'); 
                    }  
                    action 'Move objects' : PhysicalFunction  { 
                        @CapellaID { eid = "209f023e-f10e-472d-b0c1-3d6310e5f1f9"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outObjects' : FunctionOutputPort  { 
                            @CapellaID { eid = "a55d4a11-de2d-4879-815c-c819e824de08"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Move objects'.'outObjects'); 
                    }  
                    action 'Provide diverse terrain' : PhysicalFunction  { 
                        @CapellaID { eid = "ae56c15c-5bd1-475b-860d-61871c26369f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outTerrain' : FunctionOutputPort  { 
                            @CapellaID { eid = "37001d72-9374-40cb-98b2-55456a66d340"; } 
                            attribute :>> isControl = false; 
                            attribute :>> isControlType = false; 
                            attribute :>> kindOfNode = ObjectNodeKind::Unspecified; 
                            attribute :>> ordering = ObjectNodeOrderingKind::FIFO; 
                             
                        }  
                        in port 'inWeather' : FunctionInputPort  { 
                            @CapellaID { eid = "71dbfe5e-ff40-490a-a057-db7c9bdad999"; } 
                            attribute :>> isControl = false; 
                            attribute :>> isControlType = false; 
                            attribute :>> kindOfNode = ObjectNodeKind::Unspecified; 
                            attribute :>> ordering = ObjectNodeOrderingKind::FIFO; 
                             
                        }  
                        in port 'inLocation' : FunctionInputPort  { 
                            @CapellaID { eid = "5fb33831-b267-4f71-b846-176e401f97d7"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Provide diverse terrain'.'outTerrain'); 
                        ref :>> inputs =  ('eRod_Autonomous_Vehicle_2024 Project'::'eRod_Autonomous_Vehicle_2024'::'Physical Architecture'::'Physical Functions'::'Root Physical Function'.'Provide diverse terrain'.'inWeather',
                        'eRod_Autonomous_Vehicle_2024 Project'::'eRod_Autonomous_Vehicle_2024'::'Physical Architecture'::'Physical Functions'::'Root Physical Function'.'Provide diverse terrain'.'inLocation'); 
                    }  
                    action 'Maintain speed' : PhysicalFunction  { 
                        @CapellaID { eid = "e8466119-2dbf-49f5-9f99-18d7827491e2"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 2' : FunctionInputPort  { 
                            @CapellaID { eid = "20d7c587-8b83-4f02-90ed-cc52c963df81"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Physical Architecture'::'Physical Functions'::'Root Physical Function'.'Maintain speed'.'FIP 2'); 
                    }  
                    action 'Resist Front Wheels' : PhysicalFunction  { 
                        @CapellaID { eid = "ff3f32dc-da21-486f-b661-5aaf030dd2d7"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "190bc7a0-fe9b-4de5-93a0-c447f66fcd54"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Physical Architecture'::'Physical Functions'::'Root Physical Function'.'Resist Front Wheels'.'FIP 1'); 
                    }  
                    action 'Informed Software update' : PhysicalFunction  { 
                        @CapellaID { eid = "828ffbe0-267e-4aea-996a-3570988b7199"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outApproval' : FunctionOutputPort  { 
                            @CapellaID { eid = "ad77ba09-ff48-41d8-8316-7691d5aff2fc"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Informed Software update'.'outApproval'); 
                    }  
                    action 'Drive vehicle' : PhysicalFunction  { 
                        @CapellaID { eid = "1ccba46d-7f27-448d-a1c4-34d0965d0927"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "34e55263-083c-4c99-be38-02c875aaefb6"; } 
                            attribute :>> isControl = false; 
                            attribute :>> isControlType = false; 
                            attribute :>> kindOfNode = ObjectNodeKind::Unspecified; 
                            attribute :>> ordering = ObjectNodeOrderingKind::FIFO; 
                            ref :>> outgoingExchangeItems =  ('eRod_Autonomous_Vehicle_2024 Project'::'eRod_Autonomous_Vehicle_2024'::'Physical Architecture'::'Data'::'Steering Force',
                            'eRod_Autonomous_Vehicle_2024 Project'::'eRod_Autonomous_Vehicle_2024'::'Physical Architecture'::'Data'::'Steering Angle'); 
                             
                        }  
                        out port 'FOP 2' : FunctionOutputPort  { 
                            @CapellaID { eid = "037e1a20-3c35-47e2-927b-93d8fc2099d7"; } 
                            attribute :>> isControl = false; 
                            attribute :>> isControlType = false; 
                            attribute :>> kindOfNode = ObjectNodeKind::Unspecified; 
                            attribute :>> ordering = ObjectNodeOrderingKind::FIFO; 
                             
                        }  
                        out port 'FOP 3' : FunctionOutputPort  { 
                            @CapellaID { eid = "ba304014-6353-4571-a658-8c9ed2aa1c18"; } 
                            attribute :>> isControl = false; 
                            attribute :>> isControlType = false; 
                            attribute :>> kindOfNode = ObjectNodeKind::Unspecified; 
                            attribute :>> ordering = ObjectNodeOrderingKind::FIFO; 
                             
                        }  
                        out port 'outLocation' : FunctionOutputPort  { 
                            @CapellaID { eid = "6d465ccf-7ead-4047-a555-acd324237aa3"; } 
                            attribute :>> isControl = false; 
                            attribute :>> isControlType = false; 
                            attribute :>> kindOfNode = ObjectNodeKind::Unspecified; 
                            attribute :>> ordering = ObjectNodeOrderingKind::FIFO; 
                             
                        }  
                        in port 'inTerrain' : FunctionInputPort  { 
                            @CapellaID { eid = "39333812-96ec-454a-8324-4ed52b02575b"; } 
                            attribute :>> isControl = false; 
                            attribute :>> isControlType = false; 
                            attribute :>> kindOfNode = ObjectNodeKind::Unspecified; 
                            attribute :>> ordering = ObjectNodeOrderingKind::FIFO; 
                             
                        }  
                        in port 'inObjects' : FunctionInputPort  { 
                            @CapellaID { eid = "56cc5e2a-6c57-434f-b6ed-c06735c00807"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Drive vehicle'.'FOP 1',
                        'eRod_Autonomous_Vehicle_2024 Project'::'eRod_Autonomous_Vehicle_2024'::'Physical Architecture'::'Physical Functions'::'Root Physical Function'.'Drive vehicle'.'FOP 2',
                        'eRod_Autonomous_Vehicle_2024 Project'::'eRod_Autonomous_Vehicle_2024'::'Physical Architecture'::'Physical Functions'::'Root Physical Function'.'Drive vehicle'.'FOP 3',
                        'eRod_Autonomous_Vehicle_2024 Project'::'eRod_Autonomous_Vehicle_2024'::'Physical Architecture'::'Physical Functions'::'Root Physical Function'.'Drive vehicle'.'outLocation'); 
                        ref :>> inputs =  ('eRod_Autonomous_Vehicle_2024 Project'::'eRod_Autonomous_Vehicle_2024'::'Physical Architecture'::'Physical Functions'::'Root Physical Function'.'Drive vehicle'.'inTerrain',
                        'eRod_Autonomous_Vehicle_2024 Project'::'eRod_Autonomous_Vehicle_2024'::'Physical Architecture'::'Physical Functions'::'Root Physical Function'.'Drive vehicle'.'inObjects'); 
                    }  
                    action 'Detect obstacles' : PhysicalFunction  { 
                        @CapellaID { eid = "6cfe293c-6727-4455-a3fa-28ff7230146a"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "defb8dc9-dd23-401a-9da4-732c958d6354"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Physical Architecture'::'Physical Functions'::'Root Physical Function'.'Detect obstacles'.'FIP 1'); 
                    }  
                    action 'Detect intersections' : PhysicalFunction  { 
                        @CapellaID { eid = "d359aa91-c1d4-494e-b88f-b08843739048"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "7d1f48c9-a975-4ad3-b0f0-4006162e5def"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Physical Architecture'::'Physical Functions'::'Root Physical Function'.'Detect intersections'.'FIP 1'); 
                    }  
                    action 'Detect road' : PhysicalFunction  { 
                        @CapellaID { eid = "75feab54-eec3-4c0b-93dd-87e764fdcea2"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        action 'Capture view' : PhysicalFunction  { 
                            @CapellaID { eid = "02fe5d0d-2f34-435a-b941-9bd2e05c3508"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "8529925e-1817-4990-bf8c-07c742447034"; } 
                                attribute :>> isControl = false; 
                                attribute :>> isControlType = false; 
                                attribute :>> kindOfNode = ObjectNodeKind::Unspecified; 
                                attribute :>> ordering = ObjectNodeOrderingKind::FIFO; 
                                 
                            }  
                            in port 'FIP 2' : FunctionInputPort  { 
                                @CapellaID { eid = "1fbae76f-9007-4468-bca8-266db94736c6"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "48892340-5b67-4827-8c69-a4b146a5d1bb"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Physical Architecture'::'Physical Functions'::'Root Physical Function'.'Detect road'.'Capture view'.'FOP 1'); 
                            ref :>> inputs =  ('eRod_Autonomous_Vehicle_2024 Project'::'eRod_Autonomous_Vehicle_2024'::'Physical Architecture'::'Physical Functions'::'Root Physical Function'.'Detect road'.'Capture view'.'FIP 2',
                            'eRod_Autonomous_Vehicle_2024 Project'::'eRod_Autonomous_Vehicle_2024'::'Physical Architecture'::'Physical Functions'::'Root Physical Function'.'Detect road'.'Capture view'.'FIP 1'); 
                        }  
                        action 'Image fusion' : PhysicalFunction  { 
                            @CapellaID { eid = "54d6541d-c24e-4b8e-bd5f-0ceb02276156"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "221f32a8-c137-4690-933e-5a2cc3ca3dbf"; } 
                                attribute :>> isControl = false; 
                                attribute :>> isControlType = false; 
                                attribute :>> kindOfNode = ObjectNodeKind::Unspecified; 
                                attribute :>> ordering = ObjectNodeOrderingKind::FIFO; 
                                 
                            }  
                            out port 'FOP 2' : FunctionOutputPort  { 
                                @CapellaID { eid = "a44e2da9-6e1e-49b7-bc16-27c21e384797"; } 
                                attribute :>> isControl = false; 
                                attribute :>> isControlType = false; 
                                attribute :>> kindOfNode = ObjectNodeKind::Unspecified; 
                                attribute :>> ordering = ObjectNodeOrderingKind::FIFO; 
                                 
                            }  
                            out port 'FOP 3' : FunctionOutputPort  { 
                                @CapellaID { eid = "0baed759-2d06-494f-ae11-4fac6b8c117a"; } 
                                attribute :>> isControl = false; 
                                attribute :>> isControlType = false; 
                                attribute :>> kindOfNode = ObjectNodeKind::Unspecified; 
                                attribute :>> ordering = ObjectNodeOrderingKind::FIFO; 
                                 
                            }  
                            out port 'FOP 4' : FunctionOutputPort  { 
                                @CapellaID { eid = "d49ab94d-2b19-4dc2-a27e-3fc34e7e0f9d"; } 
                                attribute :>> isControl = false; 
                                attribute :>> isControlType = false; 
                                attribute :>> kindOfNode = ObjectNodeKind::Unspecified; 
                                attribute :>> ordering = ObjectNodeOrderingKind::FIFO; 
                                 
                            }  
                            out port 'FOP 5' : FunctionOutputPort  { 
                                @CapellaID { eid = "6af202d0-dc07-4b33-a647-742e6f8d9c1c"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "043f90fe-b015-437c-b6ac-64c48ae686a7"; } 
                                attribute :>> isControl = false; 
                                attribute :>> isControlType = false; 
                                attribute :>> kindOfNode = ObjectNodeKind::Unspecified; 
                                attribute :>> ordering = ObjectNodeOrderingKind::FIFO; 
                                 
                            }  
                            in port 'FIP 2' : FunctionInputPort  { 
                                @CapellaID { eid = "42d02fef-94bb-4133-a71f-7545336e2de3"; } 
                                attribute :>> isControl = false; 
                                attribute :>> isControlType = false; 
                                attribute :>> kindOfNode = ObjectNodeKind::Unspecified; 
                                attribute :>> ordering = ObjectNodeOrderingKind::FIFO; 
                                 
                            }  
                            in port 'FIP 3' : FunctionInputPort  { 
                                @CapellaID { eid = "356515e9-cd21-413e-8f7a-1dd641dc0894"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Physical Architecture'::'Physical Functions'::'Root Physical Function'.'Detect road'.'Image fusion'.'FOP 1',
                            'eRod_Autonomous_Vehicle_2024 Project'::'eRod_Autonomous_Vehicle_2024'::'Physical Architecture'::'Physical Functions'::'Root Physical Function'.'Detect road'.'Image fusion'.'FOP 2',
                            'eRod_Autonomous_Vehicle_2024 Project'::'eRod_Autonomous_Vehicle_2024'::'Physical Architecture'::'Physical Functions'::'Root Physical Function'.'Detect road'.'Image fusion'.'FOP 3',
                            'eRod_Autonomous_Vehicle_2024 Project'::'eRod_Autonomous_Vehicle_2024'::'Physical Architecture'::'Physical Functions'::'Root Physical Function'.'Detect road'.'Image fusion'.'FOP 4',
                            'eRod_Autonomous_Vehicle_2024 Project'::'eRod_Autonomous_Vehicle_2024'::'Physical Architecture'::'Physical Functions'::'Root Physical Function'.'Detect road'.'Image fusion'.'FOP 5'); 
                            ref :>> inputs =  ('eRod_Autonomous_Vehicle_2024 Project'::'eRod_Autonomous_Vehicle_2024'::'Physical Architecture'::'Physical Functions'::'Root Physical Function'.'Detect road'.'Image fusion'.'FIP 1',
                            'eRod_Autonomous_Vehicle_2024 Project'::'eRod_Autonomous_Vehicle_2024'::'Physical Architecture'::'Physical Functions'::'Root Physical Function'.'Detect road'.'Image fusion'.'FIP 2',
                            'eRod_Autonomous_Vehicle_2024 Project'::'eRod_Autonomous_Vehicle_2024'::'Physical Architecture'::'Physical Functions'::'Root Physical Function'.'Detect road'.'Image fusion'.'FIP 3'); 
                        }  
                        action 'Detect path' : PhysicalFunction  { 
                            @CapellaID { eid = "d88735ad-6709-491c-9275-528bfba2f21b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = FunctionKind::FUNCTION; 
                            attribute :>> isMaxInclusive = false; 
                            attribute :>> isMinInclusive = false; 
                            attribute :>> isOrdered = false; 
                            attribute :>> isUnique = false; 
                            out port 'FOP 1' : FunctionOutputPort  { 
                                @CapellaID { eid = "03eb36cf-a0fb-4ee6-a9a4-5d67504f23a1"; } 
                                attribute :>> isControl = false; 
                                attribute :>> isControlType = false; 
                                attribute :>> kindOfNode = ObjectNodeKind::Unspecified; 
                                attribute :>> ordering = ObjectNodeOrderingKind::FIFO; 
                                 
                            }  
                            in port 'FIP 1' : FunctionInputPort  { 
                                @CapellaID { eid = "e36db9d1-191a-441f-9695-600cb1af882a"; } 
                                attribute :>> isControl = false; 
                                attribute :>> isControlType = false; 
                                attribute :>> kindOfNode = ObjectNodeKind::Unspecified; 
                                attribute :>> ordering = ObjectNodeOrderingKind::FIFO; 
                                 
                            }  
                             
                            ref :>> outputs =  ('eRod_Autonomous_Vehicle_2024 Project'::'eRod_Autonomous_Vehicle_2024'::'Physical Architecture'::'Physical Functions'::'Root Physical Function'.'Detect road'.'Detect path'.'FOP 1'); 
                            ref :>> inputs =  ('eRod_Autonomous_Vehicle_2024 Project'::'eRod_Autonomous_Vehicle_2024'::'Physical Architecture'::'Physical Functions'::'Root Physical Function'.'Detect road'.'Detect path'.'FIP 1'); 
                        }  
                        interface '96bd69e2-5156-4cb4-8fff-fbf0bbbf8206' : FunctionalExchange 
                            connect source ::> 'eRod_Autonomous_Vehicle_2024 Project'::'eRod_Autonomous_Vehicle_2024'::'Physical Architecture'::'Physical Functions'::'Root Physical Function'.'Detect road'.'Capture view'.'FOP 1'
                            to target ::> 'eRod_Autonomous_Vehicle_2024 Project'::'eRod_Autonomous_Vehicle_2024'::'Physical Architecture'::'Physical Functions'::'Root Physical Function'.'Detect road'.'Image fusion'.'FIP 1' { 
                            @CapellaID { eid = "96bd69e2-5156-4cb4-8fff-fbf0bbbf8206"; } 
                            attribute :>> isMulticast = false; 
                            attribute :>> isMultireceive = false; 
                            attribute :>> kindOfRate = RateKind::Unspecified; 
                            attribute :>> interfaceName = "Video stream"; 
                             
                        }  
                         
                        ref :>> ownedFunctions =  ('eRod_Autonomous_Vehicle_2024 Project'::'eRod_Autonomous_Vehicle_2024'::'Physical Architecture'::'Physical Functions'::'Root Physical Function'.'Detect road'.'Capture view',
                        'eRod_Autonomous_Vehicle_2024 Project'::'eRod_Autonomous_Vehicle_2024'::'Physical Architecture'::'Physical Functions'::'Root Physical Function'.'Detect road'.'Image fusion',
                        'eRod_Autonomous_Vehicle_2024 Project'::'eRod_Autonomous_Vehicle_2024'::'Physical Architecture'::'Physical Functions'::'Root Physical Function'.'Detect road'.'Detect path'); 
                        ref :>> ownedFunctionalExchanges =  ('eRod_Autonomous_Vehicle_2024 Project'::'eRod_Autonomous_Vehicle_2024'::'Physical Architecture'::'Physical Functions'::'Root Physical Function'.'Detect road'.'96bd69e2-5156-4cb4-8fff-fbf0bbbf8206'); 
                    }  
                    action 'Detect signs' : PhysicalFunction  { 
                        @CapellaID { eid = "20d3e158-ccce-49af-a3e4-9b96c2f092d7"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "a01a3814-eb88-41e2-b6b4-c0e93aecb8d9"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Physical Architecture'::'Physical Functions'::'Root Physical Function'.'Detect signs'.'FIP 1'); 
                    }  
                    action 'Provide weather' : PhysicalFunction  { 
                        @CapellaID { eid = "f94ecca2-c754-4c70-a731-e2abe526181c"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'outWeather' : FunctionOutputPort  { 
                            @CapellaID { eid = "128214e7-9fd3-449e-9d61-3981f746bdb9"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Provide weather'.'outWeather'); 
                    }  
                    action 'Provide road markers' : PhysicalFunction  { 
                        @CapellaID { eid = "fa231fdd-a382-4680-a21e-9d567fea8de6"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "1e17a1ae-7a5a-4485-8af5-f9a089312feb"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Provide road markers'.'FOP 1'); 
                    }  
                    action 'Detect lights' : PhysicalFunction  { 
                        @CapellaID { eid = "9514f8aa-ee91-4c79-abfc-8a3765666389"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        in port 'FIP 1' : FunctionInputPort  { 
                            @CapellaID { eid = "91048a4f-3404-46b9-991e-b3ef6e003aaa"; } 
                            attribute :>> isControl = false; 
                            attribute :>> isControlType = false; 
                            attribute :>> kindOfNode = ObjectNodeKind::Unspecified; 
                            attribute :>> ordering = ObjectNodeOrderingKind::FIFO; 
                             
                        }  
                         
                        ref :>> inputs =  ('eRod_Autonomous_Vehicle_2024 Project'::'eRod_Autonomous_Vehicle_2024'::'Physical Architecture'::'Physical Functions'::'Root Physical Function'.'Detect lights'.'FIP 1'); 
                    }  
                    action 'Capture points' : PhysicalFunction  { 
                        @CapellaID { eid = "407e26c7-4b8e-438b-abb9-83436a6d388b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "ce809761-f394-45ff-9cb8-d51659504119"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Capture points'.'FOP 1'); 
                    }  
                    action 'Capture radar echo' : PhysicalFunction  { 
                        @CapellaID { eid = "1664c0e0-36ae-4800-ac5f-a6fda135b2c1"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 1' : FunctionOutputPort  { 
                            @CapellaID { eid = "3359c585-2bd8-4680-a141-60e03af0ecd8"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Capture radar echo'.'FOP 1'); 
                    }  
                    action 'Avoid collision' : PhysicalFunction  { 
                        @CapellaID { eid = "cbd83804-0972-430c-ab52-2ac24a399713"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = FunctionKind::FUNCTION; 
                        attribute :>> isMaxInclusive = false; 
                        attribute :>> isMinInclusive = false; 
                        attribute :>> isOrdered = false; 
                        attribute :>> isUnique = false; 
                        out port 'FOP 3' : FunctionOutputPort  { 
                            @CapellaID { eid = "9d526c02-71f8-4c06-9e7b-b5511b961eff"; } 
                            attribute :>> isControl = false; 
                            attribute :>> isControlType = false; 
                            attribute :>> kindOfNode = ObjectNodeKind::Unspecified; 
                            attribute :>> ordering = ObjectNodeOrderingKind::FIFO; 
                             
                        }  
                         
                        ref :>> outputs =  ('eRod_Autonomous_Vehicle_2024 Project'::'eRod_Autonomous_Vehicle_2024'::'Physical Architecture'::'Physical Functions'::'Root Physical Function'.'Avoid collision'.'FOP 3'); 
                    }  
                    interface '9b4000bd-c473-4c80-a275-48cb0e12156f' : FunctionalExchange 
                        connect source ::> 'eRod_Autonomous_Vehicle_2024 Project'::'eRod_Autonomous_Vehicle_2024'::'Physical Architecture'::'Physical Functions'::'Root Physical Function'.'Stop'.'outProvide'
                        to target ::> 'eRod_Autonomous_Vehicle_2024 Project'::'eRod_Autonomous_Vehicle_2024'::'Physical Architecture'::'Physical Functions'::'Root Physical Function'.'Car racing experience absorbed'.'inProvide' { 
                        @CapellaID { eid = "9b4000bd-c473-4c80-a275-48cb0e12156f"; } 
                        attribute :>> isMulticast = false; 
                        attribute :>> isMultireceive = false; 
                        attribute :>> kindOfRate = RateKind::Unspecified; 
                        attribute :>> interfaceName = "Cause"; 
                         
                    }  
                    interface '4e03206e-6b66-41ae-9545-cc5cbb1ce6ac' : FunctionalExchange 
                        connect source ::> 'eRod_Autonomous_Vehicle_2024 Project'::'eRod_Autonomous_Vehicle_2024'::'Physical Architecture'::'Physical Functions'::'Root Physical Function'.'Motor overheating warning '.'outDisplay'
                        to target ::> 'eRod_Autonomous_Vehicle_2024 Project'::'eRod_Autonomous_Vehicle_2024'::'Physical Architecture'::'Physical Functions'::'Root Physical Function'.'Get informed with issues'.'inDisplay' { 
                        @CapellaID { eid = "4e03206e-6b66-41ae-9545-cc5cbb1ce6ac"; } 
                        attribute :>> isMulticast = false; 
                        attribute :>> isMultireceive = false; 
                        attribute :>> kindOfRate = RateKind::Unspecified; 
                        attribute :>> interfaceName = "Display"; 
                         
                    }  
                    interface '456055aa-4b85-43b2-8567-70e2f0fad6bf' : FunctionalExchange 
                        connect source ::> 'eRod_Autonomous_Vehicle_2024 Project'::'eRod_Autonomous_Vehicle_2024'::'Physical Architecture'::'Physical Functions'::'Root Physical Function'.'Motor Start'.'outCause'
                        to target ::> 'eRod_Autonomous_Vehicle_2024 Project'::'eRod_Autonomous_Vehicle_2024'::'Physical Architecture'::'Physical Functions'::'Root Physical Function'.'Transfer Energy'.'Acquire electrical Energy'.'FIP 1' { 
                        @CapellaID { eid = "456055aa-4b85-43b2-8567-70e2f0fad6bf"; } 
                        attribute :>> isMulticast = false; 
                        attribute :>> isMultireceive = false; 
                        attribute :>> kindOfRate = RateKind::Unspecified; 
                        attribute :>> interfaceName = "Signal"; 
                         
                    }  
                    interface '5c452de6-54ad-4990-a4d6-eb8f0c3acb34' : FunctionalExchange 
                        connect source ::> 'eRod_Autonomous_Vehicle_2024 Project'::'eRod_Autonomous_Vehicle_2024'::'Physical Architecture'::'Physical Functions'::'Root Physical Function'.'Get informed with issues'.'FOP 1'
                        to target ::> 'eRod_Autonomous_Vehicle_2024 Project'::'eRod_Autonomous_Vehicle_2024'::'Physical Architecture'::'Physical Functions'::'Root Physical Function'.'Report issues'.'FIP 1' { 
                        @CapellaID { eid = "5c452de6-54ad-4990-a4d6-eb8f0c3acb34"; } 
                        attribute :>> isMulticast = false; 
                        attribute :>> isMultireceive = false; 
                        attribute :>> kindOfRate = RateKind::Unspecified; 
                        attribute :>> interfaceName = "action"; 
                         
                    }  
                    interface '3e32e08c-4ec4-4d11-984b-e71b9f8a7eba' : FunctionalExchange 
                        connect source ::> 'eRod_Autonomous_Vehicle_2024 Project'::'eRod_Autonomous_Vehicle_2024'::'Physical Architecture'::'Physical Functions'::'Root Physical Function'.'Drive on a race track'.'outCommand'
                        to target ::> 'eRod_Autonomous_Vehicle_2024 Project'::'eRod_Autonomous_Vehicle_2024'::'Physical Architecture'::'Physical Functions'::'Root Physical Function'.'Motor Start'.'FIP 2' { 
                        @CapellaID { eid = "3e32e08c-4ec4-4d11-984b-e71b9f8a7eba"; } 
                        attribute :>> isMulticast = false; 
                        attribute :>> isMultireceive = false; 
                        attribute :>> kindOfRate = RateKind::Unspecified; 
                        attribute :>> interfaceName = "Command"; 
                         
                    }  
                    interface '3323da4e-ac6a-472c-8e08-4f552dc0e710' : FunctionalExchange 
                        connect source ::> 'eRod_Autonomous_Vehicle_2024 Project'::'eRod_Autonomous_Vehicle_2024'::'Physical Architecture'::'Physical Functions'::'Root Physical Function'.'Motor protect'.'Detect temperature limit'.'FOP 3'
                        to target ::> 'eRod_Autonomous_Vehicle_2024 Project'::'eRod_Autonomous_Vehicle_2024'::'Physical Architecture'::'Physical Functions'::'Root Physical Function'.'Motor overheating warning '.'inCause' { 
                        @CapellaID { eid = "3323da4e-ac6a-472c-8e08-4f552dc0e710"; } 
                        attribute :>> isMulticast = false; 
                        attribute :>> isMultireceive = false; 
                        attribute :>> kindOfRate = RateKind::Unspecified; 
                        attribute :>> interfaceName = "Display signal"; 
                         
                    }  
                    interface '1bc640fb-b164-4519-b71d-d0dd4c284f64' : FunctionalExchange 
                        connect source ::> 'eRod_Autonomous_Vehicle_2024 Project'::'eRod_Autonomous_Vehicle_2024'::'Physical Architecture'::'Physical Functions'::'Root Physical Function'.'Deaccelerate'.'FOP 1'
                        to target ::> 'eRod_Autonomous_Vehicle_2024 Project'::'eRod_Autonomous_Vehicle_2024'::'Physical Architecture'::'Physical Functions'::'Root Physical Function'.'Stop'.'FIP 1' { 
                        @CapellaID { eid = "1bc640fb-b164-4519-b71d-d0dd4c284f64"; } 
                        attribute :>> isMulticast = false; 
                        attribute :>> isMultireceive = false; 
                        attribute :>> kindOfRate = RateKind::Unspecified; 
                        attribute :>> interfaceName = "Energy"; 
                         
                    }  
                    interface 'dffd79cd-b8f3-416a-843c-0f9d05a57d2a' : FunctionalExchange 
                        connect source ::> 'eRod_Autonomous_Vehicle_2024 Project'::'eRod_Autonomous_Vehicle_2024'::'Physical Architecture'::'Physical Functions'::'Root Physical Function'.'Report issues'.'FOP 1'
                        to target ::> 'eRod_Autonomous_Vehicle_2024 Project'::'eRod_Autonomous_Vehicle_2024'::'Physical Architecture'::'Physical Functions'::'Root Physical Function'.'Software update'.'inFeedback' { 
                        @CapellaID { eid = "dffd79cd-b8f3-416a-843c-0f9d05a57d2a"; } 
                        attribute :>> isMulticast = false; 
                        attribute :>> isMultireceive = false; 
                        attribute :>> kindOfRate = RateKind::Unspecified; 
                        attribute :>> interfaceName = "Information"; 
                         
                    }  
                    interface 'c4d37336-ab25-492f-b4b6-351feb813405' : FunctionalExchange 
                        connect source ::> 'eRod_Autonomous_Vehicle_2024 Project'::'eRod_Autonomous_Vehicle_2024'::'Physical Architecture'::'Physical Functions'::'Root Physical Function'.'Get Software-update'.'FOP 1'
                        to target ::> 'eRod_Autonomous_Vehicle_2024 Project'::'eRod_Autonomous_Vehicle_2024'::'Physical Architecture'::'Physical Functions'::'Root Physical Function'.'Software update'.'inFeedback' { 
                        @CapellaID { eid = "c4d37336-ab25-492f-b4b6-351feb813405"; } 
                        attribute :>> isMulticast = false; 
                        attribute :>> isMultireceive = false; 
                        attribute :>> kindOfRate = RateKind::Unspecified; 
                        attribute :>> interfaceName = "enable"; 
                         
                    }  
                    interface '3456a6a1-0825-47fd-bafc-064d5940fc0c' : FunctionalExchange 
                        connect source ::> 'eRod_Autonomous_Vehicle_2024 Project'::'eRod_Autonomous_Vehicle_2024'::'Physical Architecture'::'Physical Functions'::'Root Physical Function'.'Transfer Energy'.'Acquire electrical Energy'.'FOP 1'
                        to target ::> 'eRod_Autonomous_Vehicle_2024 Project'::'eRod_Autonomous_Vehicle_2024'::'Physical Architecture'::'Physical Functions'::'Root Physical Function'.'deliver mechanical power'.'FIP 1' { 
                        @CapellaID { eid = "3456a6a1-0825-47fd-bafc-064d5940fc0c"; } 
                        attribute :>> isMulticast = false; 
                        attribute :>> isMultireceive = false; 
                        attribute :>> kindOfRate = RateKind::Unspecified; 
                        attribute :>> interfaceName = "Electricity"; 
                         
                    }  
                    interface '263913cb-fa3b-4d7a-8f60-9cb9c8fb507a' : FunctionalExchange 
                        connect source ::> 'eRod_Autonomous_Vehicle_2024 Project'::'eRod_Autonomous_Vehicle_2024'::'Physical Architecture'::'Physical Functions'::'Root Physical Function'.'Transfer Energy'.'Acquire electrical Energy'.'FOP 2'
                        to target ::> 'eRod_Autonomous_Vehicle_2024 Project'::'eRod_Autonomous_Vehicle_2024'::'Physical Architecture'::'Physical Functions'::'Root Physical Function'.'Provide magnetic field'.'FIP 1' { 
                        @CapellaID { eid = "263913cb-fa3b-4d7a-8f60-9cb9c8fb507a"; } 
                        attribute :>> isMulticast = false; 
                        attribute :>> isMultireceive = false; 
                        attribute :>> kindOfRate = RateKind::Unspecified; 
                        attribute :>> interfaceName = "Electricity"; 
                         
                    }  
                    interface 'bf906ee8-dedd-4fe1-91d5-f7853ff901ae' : FunctionalExchange 
                        connect source ::> 'eRod_Autonomous_Vehicle_2024 Project'::'eRod_Autonomous_Vehicle_2024'::'Physical Architecture'::'Physical Functions'::'Root Physical Function'.'deliver mechanical power'.'FOP 1'
                        to target ::> 'eRod_Autonomous_Vehicle_2024 Project'::'eRod_Autonomous_Vehicle_2024'::'Physical Architecture'::'Physical Functions'::'Root Physical Function'.'Generate heat (Rotor)'.'FIP 1' { 
                        @CapellaID { eid = "bf906ee8-dedd-4fe1-91d5-f7853ff901ae"; } 
                        attribute :>> isMulticast = false; 
                        attribute :>> isMultireceive = false; 
                        attribute :>> kindOfRate = RateKind::Unspecified; 
                        attribute :>> interfaceName = "energy losses"; 
                         
                    }  
                    interface 'e7d77080-1205-48b7-922e-54b69ae5eb6e' : FunctionalExchange 
                        connect source ::> 'eRod_Autonomous_Vehicle_2024 Project'::'eRod_Autonomous_Vehicle_2024'::'Physical Architecture'::'Physical Functions'::'Root Physical Function'.'Provide magnetic field'.'FOP 1'
                        to target ::> 'eRod_Autonomous_Vehicle_2024 Project'::'eRod_Autonomous_Vehicle_2024'::'Physical Architecture'::'Physical Functions'::'Root Physical Function'.'Generate Heat (Stator)'.'FIP 1' { 
                        @CapellaID { eid = "e7d77080-1205-48b7-922e-54b69ae5eb6e"; } 
                        attribute :>> isMulticast = false; 
                        attribute :>> isMultireceive = false; 
                        attribute :>> kindOfRate = RateKind::Unspecified; 
                        attribute :>> interfaceName = "energy losses"; 
                         
                    }  
                    interface '25a019eb-1f3e-4af4-910c-1c9ec88d3bbd' : FunctionalExchange 
                        connect source ::> 'eRod_Autonomous_Vehicle_2024 Project'::'eRod_Autonomous_Vehicle_2024'::'Physical Architecture'::'Physical Functions'::'Root Physical Function'.'Generate heat (Rotor)'.'FOP 1'
                        to target ::> 'eRod_Autonomous_Vehicle_2024 Project'::'eRod_Autonomous_Vehicle_2024'::'Physical Architecture'::'Physical Functions'::'Root Physical Function'.'Gather 21'.'FIP 1' { 
                        @CapellaID { eid = "25a019eb-1f3e-4af4-910c-1c9ec88d3bbd"; } 
                        attribute :>> isMulticast = false; 
                        attribute :>> isMultireceive = false; 
                        attribute :>> kindOfRate = RateKind::Unspecified; 
                        attribute :>> interfaceName = "Heat flow"; 
                         
                        ref :>> exchangedItems =  ('eRod_Autonomous_Vehicle_2024 Project'::'eRod_Autonomous_Vehicle_2024'::'Logical Architecture'::'Data'::'Heat'); 
                    }  
                    interface '56b5a67c-b469-4ef5-af7d-e1fb7e3bfcf5' : FunctionalExchange 
                        connect source ::> 'eRod_Autonomous_Vehicle_2024 Project'::'eRod_Autonomous_Vehicle_2024'::'Physical Architecture'::'Physical Functions'::'Root Physical Function'.'Generate Heat (Stator)'.'FOP 1'
                        to target ::> 'eRod_Autonomous_Vehicle_2024 Project'::'eRod_Autonomous_Vehicle_2024'::'Physical Architecture'::'Physical Functions'::'Root Physical Function'.'Gather 21'.'FIP 2' { 
                        @CapellaID { eid = "56b5a67c-b469-4ef5-af7d-e1fb7e3bfcf5"; } 
                        attribute :>> isMulticast = false; 
                        attribute :>> isMultireceive = false; 
                        attribute :>> kindOfRate = RateKind::Unspecified; 
                        attribute :>> interfaceName = "Heat flow"; 
                         
                        ref :>> exchangedItems =  ('eRod_Autonomous_Vehicle_2024 Project'::'eRod_Autonomous_Vehicle_2024'::'Logical Architecture'::'Data'::'Heat'); 
                    }  
                    interface '7ae44802-8c02-4afc-9143-cd74794cb224' : FunctionalExchange 
                        connect source ::> 'eRod_Autonomous_Vehicle_2024 Project'::'eRod_Autonomous_Vehicle_2024'::'Physical Architecture'::'Physical Functions'::'Root Physical Function'.'Transfer heat'.'FOP 1'
                        to target ::> 'eRod_Autonomous_Vehicle_2024 Project'::'eRod_Autonomous_Vehicle_2024'::'Physical Architecture'::'Physical Functions'::'Root Physical Function'.'Motor protect'.'Monitor temperature'.'FIP 1' { 
                        @CapellaID { eid = "7ae44802-8c02-4afc-9143-cd74794cb224"; } 
                        attribute :>> isMulticast = false; 
                        attribute :>> isMultireceive = false; 
                        attribute :>> kindOfRate = RateKind::Unspecified; 
                        attribute :>> interfaceName = "Heat flow"; 
                         
                    }  
                    interface '58863c2d-ded0-49c9-8337-1aaeec5c9015' : FunctionalExchange 
                        connect source ::> 'eRod_Autonomous_Vehicle_2024 Project'::'eRod_Autonomous_Vehicle_2024'::'Physical Architecture'::'Physical Functions'::'Root Physical Function'.'Gather 21'.'FOP 1'
                        to target ::> 'eRod_Autonomous_Vehicle_2024 Project'::'eRod_Autonomous_Vehicle_2024'::'Physical Architecture'::'Physical Functions'::'Root Physical Function'.'Transfer heat'.'FIP 1' { 
                        @CapellaID { eid = "58863c2d-ded0-49c9-8337-1aaeec5c9015"; } 
                        attribute :>> isMulticast = false; 
                        attribute :>> isMultireceive = false; 
                        attribute :>> kindOfRate = RateKind::Unspecified; 
                        attribute :>> interfaceName = "Heat flow"; 
                         
                        ref :>> exchangedItems =  ('eRod_Autonomous_Vehicle_2024 Project'::'eRod_Autonomous_Vehicle_2024'::'Logical Architecture'::'Data'::'Heat'); 
                    }  
                    interface '4deab054-027c-43d9-bdcb-0acc6b2bbd1e' : FunctionalExchange 
                        connect source ::> 'eRod_Autonomous_Vehicle_2024 Project'::'eRod_Autonomous_Vehicle_2024'::'Physical Architecture'::'Physical Functions'::'Root Physical Function'.'deliver mechanical power'.'FOP 2'
                        to target ::> 'eRod_Autonomous_Vehicle_2024 Project'::'eRod_Autonomous_Vehicle_2024'::'Physical Architecture'::'Physical Functions'::'Root Physical Function'.'Transfer power to Axies'.'FIP 1' { 
                        @CapellaID { eid = "4deab054-027c-43d9-bdcb-0acc6b2bbd1e"; } 
                        attribute :>> isMulticast = false; 
                        attribute :>> isMultireceive = false; 
                        attribute :>> kindOfRate = RateKind::Unspecified; 
                        attribute :>> interfaceName = "Torque"; 
                         
                    }  
                    interface '86db36a6-de52-4275-a1c2-d24a5d1d027e' : FunctionalExchange 
                        connect source ::> 'eRod_Autonomous_Vehicle_2024 Project'::'eRod_Autonomous_Vehicle_2024'::'Physical Architecture'::'Physical Functions'::'Root Physical Function'.'Transfer power to Axies'.'FOP 1'
                        to target ::> 'eRod_Autonomous_Vehicle_2024 Project'::'eRod_Autonomous_Vehicle_2024'::'Physical Architecture'::'Physical Functions'::'Root Physical Function'.'Apply rotation on wheels'.'FIP 1' { 
                        @CapellaID { eid = "86db36a6-de52-4275-a1c2-d24a5d1d027e"; } 
                        attribute :>> isMulticast = false; 
                        attribute :>> isMultireceive = false; 
                        attribute :>> kindOfRate = RateKind::Unspecified; 
                        attribute :>> interfaceName = "Torque"; 
                         
                    }  
                    interface 'e3f1fb22-0869-4f7a-af75-8be9de9dc08b' : FunctionalExchange 
                        connect source ::> 'eRod_Autonomous_Vehicle_2024 Project'::'eRod_Autonomous_Vehicle_2024'::'Physical Architecture'::'Physical Functions'::'Root Physical Function'.'Motor protect'.'Reduce power'.'FOP 1'
                        to target ::> 'eRod_Autonomous_Vehicle_2024 Project'::'eRod_Autonomous_Vehicle_2024'::'Physical Architecture'::'Physical Functions'::'Root Physical Function'.'deliver mechanical power'.'FIP 3' { 
                        @CapellaID { eid = "e3f1fb22-0869-4f7a-af75-8be9de9dc08b"; } 
                        attribute :>> isMulticast = false; 
                        attribute :>> isMultireceive = false; 
                        attribute :>> kindOfRate = RateKind::Unspecified; 
                        attribute :>> interfaceName = "Command"; 
                         
                    }  
                    interface 'd355c232-2f84-4da6-88be-ea3b3e3927fd' : FunctionalExchange 
                        connect source ::> 'eRod_Autonomous_Vehicle_2024 Project'::'eRod_Autonomous_Vehicle_2024'::'Physical Architecture'::'Physical Functions'::'Root Physical Function'.'Apply rotation on wheels'.'FOP 2'
                        to target ::> 'eRod_Autonomous_Vehicle_2024 Project'::'eRod_Autonomous_Vehicle_2024'::'Physical Architecture'::'Physical Functions'::'Root Physical Function'.'Split 25'.'FIP 1' { 
                        @CapellaID { eid = "d355c232-2f84-4da6-88be-ea3b3e3927fd"; } 
                        attribute :>> isMulticast = false; 
                        attribute :>> isMultireceive = false; 
                        attribute :>> kindOfRate = RateKind::Unspecified; 
                        attribute :>> interfaceName = "power"; 
                         
                    }  
                    interface 'f39aa588-fe27-4554-82db-26cf09846ede' : FunctionalExchange 
                        connect source ::> 'eRod_Autonomous_Vehicle_2024 Project'::'eRod_Autonomous_Vehicle_2024'::'Physical Architecture'::'Physical Functions'::'Root Physical Function'.'Split 25'.'FOP 1'
                        to target ::> 'eRod_Autonomous_Vehicle_2024 Project'::'eRod_Autonomous_Vehicle_2024'::'Physical Architecture'::'Physical Functions'::'Root Physical Function'.'Sporty drive'.'FIP 2' { 
                        @CapellaID { eid = "f39aa588-fe27-4554-82db-26cf09846ede"; } 
                        attribute :>> isMulticast = false; 
                        attribute :>> isMultireceive = false; 
                        attribute :>> kindOfRate = RateKind::Unspecified; 
                        attribute :>> interfaceName = "Rotation"; 
                         
                    }  
                    interface 'bba22ee9-6f29-4047-a51e-4586c707a2ab' : FunctionalExchange 
                        connect source ::> 'eRod_Autonomous_Vehicle_2024 Project'::'eRod_Autonomous_Vehicle_2024'::'Physical Architecture'::'Physical Functions'::'Root Physical Function'.'Split 25'.'FOP 2'
                        to target ::> 'eRod_Autonomous_Vehicle_2024 Project'::'eRod_Autonomous_Vehicle_2024'::'Physical Architecture'::'Physical Functions'::'Root Physical Function'.'Deaccelerate'.'FIP 1' { 
                        @CapellaID { eid = "bba22ee9-6f29-4047-a51e-4586c707a2ab"; } 
                        attribute :>> isMulticast = false; 
                        attribute :>> isMultireceive = false; 
                        attribute :>> kindOfRate = RateKind::Unspecified; 
                        attribute :>> interfaceName = "Power"; 
                         
                    }  
                    interface 'ee196aea-0c20-4dac-8b1c-fdcbfc3fa9b4' : FunctionalExchange 
                        connect source ::> 'eRod_Autonomous_Vehicle_2024 Project'::'eRod_Autonomous_Vehicle_2024'::'Physical Architecture'::'Physical Functions'::'Root Physical Function'.'Improve motor performance'.'FOP 1'
                        to target ::> 'eRod_Autonomous_Vehicle_2024 Project'::'eRod_Autonomous_Vehicle_2024'::'Physical Architecture'::'Physical Functions'::'Root Physical Function'.'Controll temperature'.'Limit power'.'FIP 2' { 
                        @CapellaID { eid = "ee196aea-0c20-4dac-8b1c-fdcbfc3fa9b4"; } 
                        attribute :>> isMulticast = false; 
                        attribute :>> isMultireceive = false; 
                        attribute :>> kindOfRate = RateKind::Unspecified; 
                        attribute :>> interfaceName = "Command"; 
                         
                    }  
                    interface 'e6396c65-fc89-49bd-9e09-86f944ff82c8' : FunctionalExchange 
                        connect source ::> 'eRod_Autonomous_Vehicle_2024 Project'::'eRod_Autonomous_Vehicle_2024'::'Physical Architecture'::'Physical Functions'::'Root Physical Function'.'Controll temperature'.'Limit power'.'FOP 2'
                        to target ::> 'eRod_Autonomous_Vehicle_2024 Project'::'eRod_Autonomous_Vehicle_2024'::'Physical Architecture'::'Physical Functions'::'Root Physical Function'.'deliver mechanical power'.'FIP 4' { 
                        @CapellaID { eid = "e6396c65-fc89-49bd-9e09-86f944ff82c8"; } 
                        attribute :>> isMulticast = false; 
                        attribute :>> isMultireceive = false; 
                        attribute :>> kindOfRate = RateKind::Unspecified; 
                        attribute :>> interfaceName = "Signal"; 
                         
                    }  
                    interface 'e40e3190-0e42-4663-bfac-33ccc696d16c' : FunctionalExchange 
                        connect source ::> 'eRod_Autonomous_Vehicle_2024 Project'::'eRod_Autonomous_Vehicle_2024'::'Physical Architecture'::'Physical Functions'::'Root Physical Function'.'Get Software-update'.'FOP 1'
                        to target ::> 'eRod_Autonomous_Vehicle_2024 Project'::'eRod_Autonomous_Vehicle_2024'::'Physical Architecture'::'Physical Functions'::'Root Physical Function'.'connected to the center'.'inApproval' { 
                        @CapellaID { eid = "e40e3190-0e42-4663-bfac-33ccc696d16c"; } 
                        attribute :>> isMulticast = false; 
                        attribute :>> isMultireceive = false; 
                        attribute :>> kindOfRate = RateKind::Unspecified; 
                        attribute :>> interfaceName = "Approval"; 
                         
                    }  
                    interface 'f6baab41-8911-4e66-8f00-539758ee0712' : FunctionalExchange 
                        connect source ::> 'eRod_Autonomous_Vehicle_2024 Project'::'eRod_Autonomous_Vehicle_2024'::'Physical Architecture'::'Physical Functions'::'Root Physical Function'.'Get Software-update'.'FOP 1'
                        to target ::> 'eRod_Autonomous_Vehicle_2024 Project'::'eRod_Autonomous_Vehicle_2024'::'Physical Architecture'::'Physical Functions'::'Root Physical Function'.'Improve motor performance'.'FIP 1' { 
                        @CapellaID { eid = "f6baab41-8911-4e66-8f00-539758ee0712"; } 
                        attribute :>> isMulticast = false; 
                        attribute :>> isMultireceive = false; 
                        attribute :>> kindOfRate = RateKind::Unspecified; 
                        attribute :>> interfaceName = "Enable"; 
                         
                    }  
                    interface 'd2daff82-a3d3-4886-bdb2-c577243622ec' : FunctionalExchange 
                        connect source ::> 'eRod_Autonomous_Vehicle_2024 Project'::'eRod_Autonomous_Vehicle_2024'::'Physical Architecture'::'Physical Functions'::'Root Physical Function'.'Provide electrical energy'.'FOP 1'
                        to target ::> 'eRod_Autonomous_Vehicle_2024 Project'::'eRod_Autonomous_Vehicle_2024'::'Physical Architecture'::'Physical Functions'::'Root Physical Function'.'Transfer Energy'.'Acquire electrical Energy'.'FIP 3' { 
                        @CapellaID { eid = "d2daff82-a3d3-4886-bdb2-c577243622ec"; } 
                        attribute :>> isMulticast = false; 
                        attribute :>> isMultireceive = false; 
                        attribute :>> kindOfRate = RateKind::Unspecified; 
                        attribute :>> interfaceName = "Electricity"; 
                         
                        ref :>> exchangedItems =  ('eRod_Autonomous_Vehicle_2024 Project'::'eRod_Autonomous_Vehicle_2024'::'Logical Architecture'::'Data'::'Electricity'); 
                    }  
                    interface '958f7393-a4d1-4939-812a-e1ec2778701b' : FunctionalExchange 
                        connect source ::> 'eRod_Autonomous_Vehicle_2024 Project'::'eRod_Autonomous_Vehicle_2024'::'Physical Architecture'::'Physical Functions'::'Root Physical Function'.'connected to the center'.'FOP 1'
                        to target ::> 'eRod_Autonomous_Vehicle_2024 Project'::'eRod_Autonomous_Vehicle_2024'::'Physical Architecture'::'Physical Functions'::'Root Physical Function'.'remote update'.'FIP 1' { 
                        @CapellaID { eid = "958f7393-a4d1-4939-812a-e1ec2778701b"; } 
                        attribute :>> isMulticast = false; 
                        attribute :>> isMultireceive = false; 
                        attribute :>> kindOfRate = RateKind::Unspecified; 
                        attribute :>> interfaceName = "enable"; 
                         
                    }  
                    interface '6b77677c-6a80-4a58-a5ea-6922399b4ff9' : FunctionalExchange 
                        connect source ::> 'eRod_Autonomous_Vehicle_2024 Project'::'eRod_Autonomous_Vehicle_2024'::'Physical Architecture'::'Physical Functions'::'Root Physical Function'.'Steer Wheels'.'Measure steering force'.'FOP 1'
                        to target ::> 'eRod_Autonomous_Vehicle_2024 Project'::'eRod_Autonomous_Vehicle_2024'::'Physical Architecture'::'Physical Functions'::'Root Physical Function'.'Steer Wheels'.'Torque steer compensation (TSC)'.'FIP 1' { 
                        @CapellaID { eid = "6b77677c-6a80-4a58-a5ea-6922399b4ff9"; } 
                        attribute :>> isMulticast = false; 
                        attribute :>> isMultireceive = false; 
                        attribute :>> kindOfRate = RateKind::Unspecified; 
                        attribute :>> interfaceName = "Steer"; 
                        ref :>> exchangedItems =  ('eRod_Autonomous_Vehicle_2024 Project'::'eRod_Autonomous_Vehicle_2024'::'Physical Architecture'::'Data'::'Steering Force'); 
                    }  
                    interface '9d9dee37-2079-419b-b8a5-dd75d6999ad4' : FunctionalExchange 
                        connect source ::> 'eRod_Autonomous_Vehicle_2024 Project'::'eRod_Autonomous_Vehicle_2024'::'Physical Architecture'::'Physical Functions'::'Root Physical Function'.'Steer Wheels'.'Torque steer compensation (TSC)'.'FOP 1'
                        to target ::> 'eRod_Autonomous_Vehicle_2024 Project'::'eRod_Autonomous_Vehicle_2024'::'Physical Architecture'::'Physical Functions'::'Root Physical Function'.'Steer Wheels'.'Assist steering'.'FIP 1' { 
                        @CapellaID { eid = "9d9dee37-2079-419b-b8a5-dd75d6999ad4"; } 
                        attribute :>> isMulticast = false; 
                        attribute :>> isMultireceive = false; 
                        attribute :>> kindOfRate = RateKind::Unspecified; 
                        attribute :>> interfaceName = "Steering commands"; 
                    }  
                    interface '6852c281-c259-46c4-86e8-68298fdc0d9f' : FunctionalExchange 
                        connect source ::> 'eRod_Autonomous_Vehicle_2024 Project'::'eRod_Autonomous_Vehicle_2024'::'Physical Architecture'::'Physical Functions'::'Root Physical Function'.'Provide weather'.'outWeather'
                        to target ::> 'eRod_Autonomous_Vehicle_2024 Project'::'eRod_Autonomous_Vehicle_2024'::'Physical Architecture'::'Physical Functions'::'Root Physical Function'.'Provide diverse terrain'.'inWeather' { 
                        @CapellaID { eid = "6852c281-c259-46c4-86e8-68298fdc0d9f"; } 
                        attribute :>> isMulticast = false; 
                        attribute :>> isMultireceive = false; 
                        attribute :>> kindOfRate = RateKind::Unspecified; 
                        attribute :>> interfaceName = "Weather"; 
                         
                    }  
                    interface '2e252c5d-7afb-41da-9e4d-8bdb27007357' : FunctionalExchange 
                        connect source ::> 'eRod_Autonomous_Vehicle_2024 Project'::'eRod_Autonomous_Vehicle_2024'::'Physical Architecture'::'Physical Functions'::'Root Physical Function'.'Reflect lights'.'Reflect Light FOP 1'
                        to target ::> 'eRod_Autonomous_Vehicle_2024 Project'::'eRod_Autonomous_Vehicle_2024'::'Physical Architecture'::'Physical Functions'::'Root Physical Function'.'Detect road'.'Capture view'.'FIP 2' { 
                        @CapellaID { eid = "2e252c5d-7afb-41da-9e4d-8bdb27007357"; } 
                        attribute :>> isMulticast = false; 
                        attribute :>> isMultireceive = false; 
                        attribute :>> kindOfRate = RateKind::Unspecified; 
                        attribute :>> interfaceName = "Reflected light"; 
                         
                    }  
                    interface 'e04176ef-bcbd-4847-a097-8577fdcff587' : FunctionalExchange 
                        connect source ::> 'eRod_Autonomous_Vehicle_2024 Project'::'eRod_Autonomous_Vehicle_2024'::'Physical Architecture'::'Physical Functions'::'Root Physical Function'.'Drive route'.'FOP 1'
                        to target ::> 'eRod_Autonomous_Vehicle_2024 Project'::'eRod_Autonomous_Vehicle_2024'::'Physical Architecture'::'Physical Functions'::'Root Physical Function'.'Steer Wheels'.'Automatic Steering'.'FIP 1' { 
                        @CapellaID { eid = "e04176ef-bcbd-4847-a097-8577fdcff587"; } 
                        attribute :>> isMulticast = false; 
                        attribute :>> isMultireceive = false; 
                        attribute :>> kindOfRate = RateKind::Unspecified; 
                        attribute :>> interfaceName = "Steer commands"; 
                         
                    }  
                    interface '2e63b9b6-b395-4be2-bd4a-aef1e86e68e5' : FunctionalExchange 
                        connect source ::> 'eRod_Autonomous_Vehicle_2024 Project'::'eRod_Autonomous_Vehicle_2024'::'Physical Architecture'::'Physical Functions'::'Root Physical Function'.'Steer Wheels'.'Force to Road Left Front'.'FOP 1'
                        to target ::> 'eRod_Autonomous_Vehicle_2024 Project'::'eRod_Autonomous_Vehicle_2024'::'Physical Architecture'::'Physical Functions'::'Root Physical Function'.'Resist Front Wheels'.'FIP 1' { 
                        @CapellaID { eid = "2e63b9b6-b395-4be2-bd4a-aef1e86e68e5"; } 
                        attribute :>> isMulticast = false; 
                        attribute :>> isMultireceive = false; 
                        attribute :>> kindOfRate = RateKind::Unspecified; 
                        attribute :>> interfaceName = "Left Tire forces"; 
                         
                    }  
                    interface '39b93495-b582-48da-8bb1-582aa8881fa3' : FunctionalExchange 
                        connect source ::> 'eRod_Autonomous_Vehicle_2024 Project'::'eRod_Autonomous_Vehicle_2024'::'Physical Architecture'::'Physical Functions'::'Root Physical Function'.'Informed Software update'.'outApproval'
                        to target ::> 'eRod_Autonomous_Vehicle_2024 Project'::'eRod_Autonomous_Vehicle_2024'::'Physical Architecture'::'Physical Functions'::'Root Physical Function'.'connected to the center'.'inApproval' { 
                        @CapellaID { eid = "39b93495-b582-48da-8bb1-582aa8881fa3"; } 
                        attribute :>> isMulticast = false; 
                        attribute :>> isMultireceive = false; 
                        attribute :>> kindOfRate = RateKind::Unspecified; 
                        attribute :>> interfaceName = "Approval"; 
                         
                    }  
                    interface '7c524b91-a90e-4535-9f95-267c0a21af4f' : FunctionalExchange 
                        connect source ::> 'eRod_Autonomous_Vehicle_2024 Project'::'eRod_Autonomous_Vehicle_2024'::'Physical Architecture'::'Physical Functions'::'Root Physical Function'.'Provide diverse terrain'.'outTerrain'
                        to target ::> 'eRod_Autonomous_Vehicle_2024 Project'::'eRod_Autonomous_Vehicle_2024'::'Physical Architecture'::'Physical Functions'::'Root Physical Function'.'Drive vehicle'.'inTerrain' { 
                        @CapellaID { eid = "7c524b91-a90e-4535-9f95-267c0a21af4f"; } 
                        attribute :>> isMulticast = false; 
                        attribute :>> isMultireceive = false; 
                        attribute :>> kindOfRate = RateKind::Unspecified; 
                        attribute :>> interfaceName = "Terrain"; 
                         
                    }  
                    interface 'd941a7b8-ebeb-49a0-8409-40002fac20ea' : FunctionalExchange 
                        connect source ::> 'eRod_Autonomous_Vehicle_2024 Project'::'eRod_Autonomous_Vehicle_2024'::'Physical Architecture'::'Physical Functions'::'Root Physical Function'.'Capture points'.'FOP 1'
                        to target ::> 'eRod_Autonomous_Vehicle_2024 Project'::'eRod_Autonomous_Vehicle_2024'::'Physical Architecture'::'Physical Functions'::'Root Physical Function'.'Detect road'.'Image fusion'.'FIP 2' { 
                        @CapellaID { eid = "d941a7b8-ebeb-49a0-8409-40002fac20ea"; } 
                        attribute :>> isMulticast = false; 
                        attribute :>> isMultireceive = false; 
                        attribute :>> kindOfRate = RateKind::Unspecified; 
                        attribute :>> interfaceName = "Point cloud"; 
                         
                    }  
                    interface '903bc69d-807f-4fa6-a826-db220b0dfa6d' : FunctionalExchange 
                        connect source ::> 'eRod_Autonomous_Vehicle_2024 Project'::'eRod_Autonomous_Vehicle_2024'::'Physical Architecture'::'Physical Functions'::'Root Physical Function'.'Capture radar echo'.'FOP 1'
                        to target ::> 'eRod_Autonomous_Vehicle_2024 Project'::'eRod_Autonomous_Vehicle_2024'::'Physical Architecture'::'Physical Functions'::'Root Physical Function'.'Detect road'.'Image fusion'.'FIP 3' { 
                        @CapellaID { eid = "903bc69d-807f-4fa6-a826-db220b0dfa6d"; } 
                        attribute :>> isMulticast = false; 
                        attribute :>> isMultireceive = false; 
                        attribute :>> kindOfRate = RateKind::Unspecified; 
                        attribute :>> interfaceName = "Point cloud"; 
                         
                    }  
                    interface '0c2c6759-00c7-4f6b-a509-f44c7a2aa1dc' : FunctionalExchange 
                        connect source ::> 'eRod_Autonomous_Vehicle_2024 Project'::'eRod_Autonomous_Vehicle_2024'::'Physical Architecture'::'Physical Functions'::'Root Physical Function'.'Avoid collision'.'FOP 3'
                        to target ::> 'eRod_Autonomous_Vehicle_2024 Project'::'eRod_Autonomous_Vehicle_2024'::'Physical Architecture'::'Physical Functions'::'Root Physical Function'.'Steer Wheels'.'Automatic Steering'.'FIP 2' { 
                        @CapellaID { eid = "0c2c6759-00c7-4f6b-a509-f44c7a2aa1dc"; } 
                        attribute :>> isMulticast = false; 
                        attribute :>> isMultireceive = false; 
                        attribute :>> kindOfRate = RateKind::Unspecified; 
                        attribute :>> interfaceName = "Evasive manuever"; 
                         
                    }  
                    interface '9a080694-6c18-47e9-9819-30442b7aaa82' : FunctionalExchange 
                        connect source ::> 'eRod_Autonomous_Vehicle_2024 Project'::'eRod_Autonomous_Vehicle_2024'::'Physical Architecture'::'Physical Functions'::'Root Physical Function'.'Drive vehicle'.'FOP 1'
                        to target ::> 'eRod_Autonomous_Vehicle_2024 Project'::'eRod_Autonomous_Vehicle_2024'::'Physical Architecture'::'Physical Functions'::'Root Physical Function'.'Steer Wheels'.'Measure steering angle'.'FIP 1' { 
                        @CapellaID { eid = "9a080694-6c18-47e9-9819-30442b7aaa82"; } 
                        attribute :>> isMulticast = false; 
                        attribute :>> isMultireceive = false; 
                        attribute :>> kindOfRate = RateKind::Unspecified; 
                        attribute :>> interfaceName = "Steering angle"; 
                         
                        ref :>> exchangedItems =  ('eRod_Autonomous_Vehicle_2024 Project'::'eRod_Autonomous_Vehicle_2024'::'Physical Architecture'::'Data'::'Steering Angle'); 
                    }  
                    interface '0f9346cb-60f7-4f52-b116-7a5eba3ad699' : FunctionalExchange 
                        connect source ::> 'eRod_Autonomous_Vehicle_2024 Project'::'eRod_Autonomous_Vehicle_2024'::'Physical Architecture'::'Physical Functions'::'Root Physical Function'.'Provide solution'.'FOP 2'
                        to target ::> 'eRod_Autonomous_Vehicle_2024 Project'::'eRod_Autonomous_Vehicle_2024'::'Physical Architecture'::'Physical Functions'::'Root Physical Function'.'Get Software-update'.'FIP 1' { 
                        @CapellaID { eid = "0f9346cb-60f7-4f52-b116-7a5eba3ad699"; } 
                        attribute :>> isMulticast = false; 
                        attribute :>> isMultireceive = false; 
                        attribute :>> kindOfRate = RateKind::Unspecified; 
                        attribute :>> interfaceName = "provide"; 
                         
                    }  
                    interface '72b2e304-b89e-4c1d-a64b-701d914c0226' : FunctionalExchange 
                        connect source ::> 'eRod_Autonomous_Vehicle_2024 Project'::'eRod_Autonomous_Vehicle_2024'::'Physical Architecture'::'Physical Functions'::'Root Physical Function'.'Drive vehicle'.'FOP 2'
                        to target ::> 'eRod_Autonomous_Vehicle_2024 Project'::'eRod_Autonomous_Vehicle_2024'::'Physical Architecture'::'Physical Functions'::'Root Physical Function'.'Slow down and stop the vehicle'.'Brake'.'FIP 1' { 
                        @CapellaID { eid = "72b2e304-b89e-4c1d-a64b-701d914c0226"; } 
                        attribute :>> isMulticast = false; 
                        attribute :>> isMultireceive = false; 
                        attribute :>> kindOfRate = RateKind::Unspecified; 
                        attribute :>> interfaceName = "Brake"; 
                         
                    }  
                    interface 'ad5502cd-ad0e-43aa-b2d7-cf0abcd36c4e' : FunctionalExchange 
                        connect source ::> 'eRod_Autonomous_Vehicle_2024 Project'::'eRod_Autonomous_Vehicle_2024'::'Physical Architecture'::'Physical Functions'::'Root Physical Function'.'Steer Wheels'.'Automatic Steering'.'FOP 1'
                        to target ::> 'eRod_Autonomous_Vehicle_2024 Project'::'eRod_Autonomous_Vehicle_2024'::'Physical Architecture'::'Physical Functions'::'Root Physical Function'.'Steer Wheels'.'FIP 1' { 
                        @CapellaID { eid = "ad5502cd-ad0e-43aa-b2d7-cf0abcd36c4e"; } 
                        attribute :>> isMulticast = false; 
                        attribute :>> isMultireceive = false; 
                        attribute :>> kindOfRate = RateKind::Unspecified; 
                        attribute :>> interfaceName = "Steer command"; 
                         
                    }  
                    interface '31a8809d-3d03-4ca1-8898-62af332f0687' : FunctionalExchange 
                        connect source ::> 'eRod_Autonomous_Vehicle_2024 Project'::'eRod_Autonomous_Vehicle_2024'::'Physical Architecture'::'Physical Functions'::'Root Physical Function'.'Drive vehicle'.'FOP 3'
                        to target ::> 'eRod_Autonomous_Vehicle_2024 Project'::'eRod_Autonomous_Vehicle_2024'::'Physical Architecture'::'Physical Functions'::'Root Physical Function'.'Maintain speed'.'FIP 2' { 
                        @CapellaID { eid = "31a8809d-3d03-4ca1-8898-62af332f0687"; } 
                        attribute :>> isMulticast = false; 
                        attribute :>> isMultireceive = false; 
                        attribute :>> kindOfRate = RateKind::Unspecified; 
                        attribute :>> interfaceName = "Accel/Decel"; 
                         
                    }  
                    interface '2b8263b6-4be5-4e78-9588-d14cbbfe6db1' : FunctionalExchange 
                        connect source ::> 'eRod_Autonomous_Vehicle_2024 Project'::'eRod_Autonomous_Vehicle_2024'::'Physical Architecture'::'Physical Functions'::'Root Physical Function'.'Drive vehicle'.'outLocation'
                        to target ::> 'eRod_Autonomous_Vehicle_2024 Project'::'eRod_Autonomous_Vehicle_2024'::'Physical Architecture'::'Physical Functions'::'Root Physical Function'.'Provide diverse terrain'.'inLocation' { 
                        @CapellaID { eid = "2b8263b6-4be5-4e78-9588-d14cbbfe6db1"; } 
                        attribute :>> isMulticast = false; 
                        attribute :>> isMultireceive = false; 
                        attribute :>> kindOfRate = RateKind::Unspecified; 
                        attribute :>> interfaceName = "Location"; 
                         
                    }  
                    interface '183930ab-9da1-4de3-b265-8497bd93ce51' : FunctionalExchange 
                        connect source ::> 'eRod_Autonomous_Vehicle_2024 Project'::'eRod_Autonomous_Vehicle_2024'::'Physical Architecture'::'Physical Functions'::'Root Physical Function'.'Move objects'.'outObjects'
                        to target ::> 'eRod_Autonomous_Vehicle_2024 Project'::'eRod_Autonomous_Vehicle_2024'::'Physical Architecture'::'Physical Functions'::'Root Physical Function'.'Drive vehicle'.'inObjects' { 
                        @CapellaID { eid = "183930ab-9da1-4de3-b265-8497bd93ce51"; } 
                        attribute :>> isMulticast = false; 
                        attribute :>> isMultireceive = false; 
                        attribute :>> kindOfRate = RateKind::Unspecified; 
                        attribute :>> interfaceName = "Objects"; 
                         
                    }  
                    interface 'f26cc61f-55b2-40ce-b8e4-5c87c1e11692' : FunctionalExchange 
                        connect source ::> 'eRod_Autonomous_Vehicle_2024 Project'::'eRod_Autonomous_Vehicle_2024'::'Physical Architecture'::'Physical Functions'::'Root Physical Function'.'Detect road'.'Image fusion'.'FOP 1'
                        to target ::> 'eRod_Autonomous_Vehicle_2024 Project'::'eRod_Autonomous_Vehicle_2024'::'Physical Architecture'::'Physical Functions'::'Root Physical Function'.'Detect obstacles'.'FIP 1' { 
                        @CapellaID { eid = "f26cc61f-55b2-40ce-b8e4-5c87c1e11692"; } 
                        attribute :>> isMulticast = false; 
                        attribute :>> isMultireceive = false; 
                        attribute :>> kindOfRate = RateKind::Unspecified; 
                        attribute :>> interfaceName = "Image data"; 
                         
                    }  
                    interface '4c223d18-1eaf-4293-b5bf-4d114649ab2b' : FunctionalExchange 
                        connect source ::> 'eRod_Autonomous_Vehicle_2024 Project'::'eRod_Autonomous_Vehicle_2024'::'Physical Architecture'::'Physical Functions'::'Root Physical Function'.'Detect road'.'Image fusion'.'FOP 2'
                        to target ::> 'eRod_Autonomous_Vehicle_2024 Project'::'eRod_Autonomous_Vehicle_2024'::'Physical Architecture'::'Physical Functions'::'Root Physical Function'.'Detect road'.'Detect path'.'FIP 1' { 
                        @CapellaID { eid = "4c223d18-1eaf-4293-b5bf-4d114649ab2b"; } 
                        attribute :>> isMulticast = false; 
                        attribute :>> isMultireceive = false; 
                        attribute :>> kindOfRate = RateKind::Unspecified; 
                        attribute :>> interfaceName = "Image data"; 
                         
                    }  
                    interface 'bb3291df-08bb-4dda-bb17-582231a87c97' : FunctionalExchange 
                        connect source ::> 'eRod_Autonomous_Vehicle_2024 Project'::'eRod_Autonomous_Vehicle_2024'::'Physical Architecture'::'Physical Functions'::'Root Physical Function'.'Provide road markers'.'FOP 1'
                        to target ::> 'eRod_Autonomous_Vehicle_2024 Project'::'eRod_Autonomous_Vehicle_2024'::'Physical Architecture'::'Physical Functions'::'Root Physical Function'.'Detect road'.'Capture view'.'FIP 1' { 
                        @CapellaID { eid = "bb3291df-08bb-4dda-bb17-582231a87c97"; } 
                        attribute :>> isMulticast = false; 
                        attribute :>> isMultireceive = false; 
                        attribute :>> kindOfRate = RateKind::Unspecified; 
                        attribute :>> interfaceName = "Road markers"; 
                         
                    }  
                    interface '39cf23bb-f26c-40c2-a631-9155541fab5d' : FunctionalExchange 
                        connect source ::> 'eRod_Autonomous_Vehicle_2024 Project'::'eRod_Autonomous_Vehicle_2024'::'Physical Architecture'::'Physical Functions'::'Root Physical Function'.'Detect road'.'Detect path'.'FOP 1'
                        to target ::> 'eRod_Autonomous_Vehicle_2024 Project'::'eRod_Autonomous_Vehicle_2024'::'Physical Architecture'::'Physical Functions'::'Root Physical Function'.'Steer Wheels'.'Automatic Steering'.'St Cmds' { 
                        @CapellaID { eid = "39cf23bb-f26c-40c2-a631-9155541fab5d"; } 
                        attribute :>> isMulticast = false; 
                        attribute :>> isMultireceive = false; 
                        attribute :>> kindOfRate = RateKind::Unspecified; 
                        attribute :>> interfaceName = "Steering commands"; 
                         
                    }  
                    interface '047e4a9b-a322-4c60-a6fe-15a5d26e63ed' : FunctionalExchange 
                        connect source ::> 'eRod_Autonomous_Vehicle_2024 Project'::'eRod_Autonomous_Vehicle_2024'::'Physical Architecture'::'Physical Functions'::'Root Physical Function'.'Detect road'.'Image fusion'.'FOP 3'
                        to target ::> 'eRod_Autonomous_Vehicle_2024 Project'::'eRod_Autonomous_Vehicle_2024'::'Physical Architecture'::'Physical Functions'::'Root Physical Function'.'Detect intersections'.'FIP 1' { 
                        @CapellaID { eid = "047e4a9b-a322-4c60-a6fe-15a5d26e63ed"; } 
                        attribute :>> isMulticast = false; 
                        attribute :>> isMultireceive = false; 
                        attribute :>> kindOfRate = RateKind::Unspecified; 
                        attribute :>> interfaceName = "Image data"; 
                         
                    }  
                    interface 'd4ce739f-b313-4ee5-87fd-97676dae628f' : FunctionalExchange 
                        connect source ::> 'eRod_Autonomous_Vehicle_2024 Project'::'eRod_Autonomous_Vehicle_2024'::'Physical Architecture'::'Physical Functions'::'Root Physical Function'.'Detect road'.'Image fusion'.'FOP 4'
                        to target ::> 'eRod_Autonomous_Vehicle_2024 Project'::'eRod_Autonomous_Vehicle_2024'::'Physical Architecture'::'Physical Functions'::'Root Physical Function'.'Detect signs'.'FIP 1' { 
                        @CapellaID { eid = "d4ce739f-b313-4ee5-87fd-97676dae628f"; } 
                        attribute :>> isMulticast = false; 
                        attribute :>> isMultireceive = false; 
                        attribute :>> kindOfRate = RateKind::Unspecified; 
                        attribute :>> interfaceName = "Image data"; 
                         
                    }  
                    interface '74d01859-163f-413f-bb52-1b476780004a' : FunctionalExchange 
                        connect source ::> 'eRod_Autonomous_Vehicle_2024 Project'::'eRod_Autonomous_Vehicle_2024'::'Physical Architecture'::'Physical Functions'::'Root Physical Function'.'Detect road'.'Image fusion'.'FOP 5'
                        to target ::> 'eRod_Autonomous_Vehicle_2024 Project'::'eRod_Autonomous_Vehicle_2024'::'Physical Architecture'::'Physical Functions'::'Root Physical Function'.'Detect lights'.'FIP 1' { 
                        @CapellaID { eid = "74d01859-163f-413f-bb52-1b476780004a"; } 
                        attribute :>> isMulticast = false; 
                        attribute :>> isMultireceive = false; 
                        attribute :>> kindOfRate = RateKind::Unspecified; 
                        attribute :>> interfaceName = "Image data"; 
                         
                    }  
                    interface '150f9456-b1c3-47b1-95df-79c543bf5015' : FunctionalExchange 
                        connect source ::> 'eRod_Autonomous_Vehicle_2024 Project'::'eRod_Autonomous_Vehicle_2024'::'Physical Architecture'::'Physical Functions'::'Root Physical Function'.'Drive vehicle'.'FOP 1'
                        to target ::> 'eRod_Autonomous_Vehicle_2024 Project'::'eRod_Autonomous_Vehicle_2024'::'Physical Architecture'::'Physical Functions'::'Root Physical Function'.'Steer Wheels'.'Measure steering force'.'FIP 1' { 
                        @CapellaID { eid = "150f9456-b1c3-47b1-95df-79c543bf5015"; } 
                        attribute :>> isMulticast = false; 
                        attribute :>> isMultireceive = false; 
                        attribute :>> kindOfRate = RateKind::Unspecified; 
                        attribute :>> interfaceName = "Steering Force"; 
                        ref :>> exchangedItems =  ('eRod_Autonomous_Vehicle_2024 Project'::'eRod_Autonomous_Vehicle_2024'::'Physical Architecture'::'Data'::'Steering Force'); 
                    }  
                    interface '05bbbd1d-69e8-4e7d-bddf-c01c48911cd4' : FunctionalExchange 
                        connect source ::> 'eRod_Autonomous_Vehicle_2024 Project'::'eRod_Autonomous_Vehicle_2024'::'Physical Architecture'::'Physical Functions'::'Root Physical Function'.'Steer Wheels'.'Force to Road Right Front'.'FOP 1'
                        to target ::> 'eRod_Autonomous_Vehicle_2024 Project'::'eRod_Autonomous_Vehicle_2024'::'Physical Architecture'::'Physical Functions'::'Root Physical Function'.'Resist Front Wheels'.'FIP 1' { 
                        @CapellaID { eid = "05bbbd1d-69e8-4e7d-bddf-c01c48911cd4"; } 
                        attribute :>> isMulticast = false; 
                        attribute :>> isMultireceive = false; 
                        attribute :>> kindOfRate = RateKind::Unspecified; 
                        attribute :>> interfaceName = "Right Tire Forces"; 
                    }  
                     
                    ref :>> ownedFunctions =  ('eRod_Autonomous_Vehicle_2024 Project'::'eRod_Autonomous_Vehicle_2024'::'Physical Architecture'::'Physical Functions'::'Root Physical Function'.'Drive on a race track',
                    'eRod_Autonomous_Vehicle_2024 Project'::'eRod_Autonomous_Vehicle_2024'::'Physical Architecture'::'Physical Functions'::'Root Physical Function'.'Sporty drive',
                    'eRod_Autonomous_Vehicle_2024 Project'::'eRod_Autonomous_Vehicle_2024'::'Physical Architecture'::'Physical Functions'::'Root Physical Function'.'Car racing experience absorbed',
                    'eRod_Autonomous_Vehicle_2024 Project'::'eRod_Autonomous_Vehicle_2024'::'Physical Architecture'::'Physical Functions'::'Root Physical Function'.'Motor overheating warning ',
                    'eRod_Autonomous_Vehicle_2024 Project'::'eRod_Autonomous_Vehicle_2024'::'Physical Architecture'::'Physical Functions'::'Root Physical Function'.'Software update',
                    'eRod_Autonomous_Vehicle_2024 Project'::'eRod_Autonomous_Vehicle_2024'::'Physical Architecture'::'Physical Functions'::'Root Physical Function'.'Report issues',
                    'eRod_Autonomous_Vehicle_2024 Project'::'eRod_Autonomous_Vehicle_2024'::'Physical Architecture'::'Physical Functions'::'Root Physical Function'.'Get informed with issues',
                    'eRod_Autonomous_Vehicle_2024 Project'::'eRod_Autonomous_Vehicle_2024'::'Physical Architecture'::'Physical Functions'::'Root Physical Function'.'Deaccelerate',
                    'eRod_Autonomous_Vehicle_2024 Project'::'eRod_Autonomous_Vehicle_2024'::'Physical Architecture'::'Physical Functions'::'Root Physical Function'.'Stop',
                    'eRod_Autonomous_Vehicle_2024 Project'::'eRod_Autonomous_Vehicle_2024'::'Physical Architecture'::'Physical Functions'::'Root Physical Function'.'Get Software-update',
                    'eRod_Autonomous_Vehicle_2024 Project'::'eRod_Autonomous_Vehicle_2024'::'Physical Architecture'::'Physical Functions'::'Root Physical Function'.'Transfer Energy',
                    'eRod_Autonomous_Vehicle_2024 Project'::'eRod_Autonomous_Vehicle_2024'::'Physical Architecture'::'Physical Functions'::'Root Physical Function'.'Motor protect',
                    'eRod_Autonomous_Vehicle_2024 Project'::'eRod_Autonomous_Vehicle_2024'::'Physical Architecture'::'Physical Functions'::'Root Physical Function'.'Controll temperature',
                    'eRod_Autonomous_Vehicle_2024 Project'::'eRod_Autonomous_Vehicle_2024'::'Physical Architecture'::'Physical Functions'::'Root Physical Function'.'deliver mechanical power',
                    'eRod_Autonomous_Vehicle_2024 Project'::'eRod_Autonomous_Vehicle_2024'::'Physical Architecture'::'Physical Functions'::'Root Physical Function'.'Generate heat (Rotor)',
                    'eRod_Autonomous_Vehicle_2024 Project'::'eRod_Autonomous_Vehicle_2024'::'Physical Architecture'::'Physical Functions'::'Root Physical Function'.'Provide magnetic field',
                    'eRod_Autonomous_Vehicle_2024 Project'::'eRod_Autonomous_Vehicle_2024'::'Physical Architecture'::'Physical Functions'::'Root Physical Function'.'Generate Heat (Stator)',
                    'eRod_Autonomous_Vehicle_2024 Project'::'eRod_Autonomous_Vehicle_2024'::'Physical Architecture'::'Physical Functions'::'Root Physical Function'.'protect',
                    'eRod_Autonomous_Vehicle_2024 Project'::'eRod_Autonomous_Vehicle_2024'::'Physical Architecture'::'Physical Functions'::'Root Physical Function'.'Transfer heat',
                    'eRod_Autonomous_Vehicle_2024 Project'::'eRod_Autonomous_Vehicle_2024'::'Physical Architecture'::'Physical Functions'::'Root Physical Function'.'Gather 21',
                    'eRod_Autonomous_Vehicle_2024 Project'::'eRod_Autonomous_Vehicle_2024'::'Physical Architecture'::'Physical Functions'::'Root Physical Function'.'Motor Start',
                    'eRod_Autonomous_Vehicle_2024 Project'::'eRod_Autonomous_Vehicle_2024'::'Physical Architecture'::'Physical Functions'::'Root Physical Function'.'Transfer power to Axies',
                    'eRod_Autonomous_Vehicle_2024 Project'::'eRod_Autonomous_Vehicle_2024'::'Physical Architecture'::'Physical Functions'::'Root Physical Function'.'Apply rotation on wheels',
                    'eRod_Autonomous_Vehicle_2024 Project'::'eRod_Autonomous_Vehicle_2024'::'Physical Architecture'::'Physical Functions'::'Root Physical Function'.'Split 25',
                    'eRod_Autonomous_Vehicle_2024 Project'::'eRod_Autonomous_Vehicle_2024'::'Physical Architecture'::'Physical Functions'::'Root Physical Function'.'Improve motor performance',
                    'eRod_Autonomous_Vehicle_2024 Project'::'eRod_Autonomous_Vehicle_2024'::'Physical Architecture'::'Physical Functions'::'Root Physical Function'.'remote update',
                    'eRod_Autonomous_Vehicle_2024 Project'::'eRod_Autonomous_Vehicle_2024'::'Physical Architecture'::'Physical Functions'::'Root Physical Function'.'connected to the center',
                    'eRod_Autonomous_Vehicle_2024 Project'::'eRod_Autonomous_Vehicle_2024'::'Physical Architecture'::'Physical Functions'::'Root Physical Function'.'Provide electrical energy',
                    'eRod_Autonomous_Vehicle_2024 Project'::'eRod_Autonomous_Vehicle_2024'::'Physical Architecture'::'Physical Functions'::'Root Physical Function'.'Pull drift compensation (PDC)',
                    'eRod_Autonomous_Vehicle_2024 Project'::'eRod_Autonomous_Vehicle_2024'::'Physical Architecture'::'Physical Functions'::'Root Physical Function'.'Active nibble compensation (ANC)',
                    'eRod_Autonomous_Vehicle_2024 Project'::'eRod_Autonomous_Vehicle_2024'::'Physical Architecture'::'Physical Functions'::'Root Physical Function'.'Arbiter/limiter (A/L)',
                    'eRod_Autonomous_Vehicle_2024 Project'::'eRod_Autonomous_Vehicle_2024'::'Physical Architecture'::'Physical Functions'::'Root Physical Function'.'Steer Feel (SF)',
                    'eRod_Autonomous_Vehicle_2024 Project'::'eRod_Autonomous_Vehicle_2024'::'Physical Architecture'::'Physical Functions'::'Root Physical Function'.'Prevent accent',
                    'eRod_Autonomous_Vehicle_2024 Project'::'eRod_Autonomous_Vehicle_2024'::'Physical Architecture'::'Physical Functions'::'Root Physical Function'.'Detect Objects',
                    'eRod_Autonomous_Vehicle_2024 Project'::'eRod_Autonomous_Vehicle_2024'::'Physical Architecture'::'Physical Functions'::'Root Physical Function'.'Provide solution',
                    'eRod_Autonomous_Vehicle_2024 Project'::'eRod_Autonomous_Vehicle_2024'::'Physical Architecture'::'Physical Functions'::'Root Physical Function'.'Slow down and stop the vehicle',
                    'eRod_Autonomous_Vehicle_2024 Project'::'eRod_Autonomous_Vehicle_2024'::'Physical Architecture'::'Physical Functions'::'Root Physical Function'.'Plan path',
                    'eRod_Autonomous_Vehicle_2024 Project'::'eRod_Autonomous_Vehicle_2024'::'Physical Architecture'::'Physical Functions'::'Root Physical Function'.'Drive route',
                    'eRod_Autonomous_Vehicle_2024 Project'::'eRod_Autonomous_Vehicle_2024'::'Physical Architecture'::'Physical Functions'::'Root Physical Function'.'Reflect lights',
                    'eRod_Autonomous_Vehicle_2024 Project'::'eRod_Autonomous_Vehicle_2024'::'Physical Architecture'::'Physical Functions'::'Root Physical Function'.'Steer Wheels',
                    'eRod_Autonomous_Vehicle_2024 Project'::'eRod_Autonomous_Vehicle_2024'::'Physical Architecture'::'Physical Functions'::'Root Physical Function'.'Move objects',
                    'eRod_Autonomous_Vehicle_2024 Project'::'eRod_Autonomous_Vehicle_2024'::'Physical Architecture'::'Physical Functions'::'Root Physical Function'.'Provide diverse terrain',
                    'eRod_Autonomous_Vehicle_2024 Project'::'eRod_Autonomous_Vehicle_2024'::'Physical Architecture'::'Physical Functions'::'Root Physical Function'.'Maintain speed',
                    'eRod_Autonomous_Vehicle_2024 Project'::'eRod_Autonomous_Vehicle_2024'::'Physical Architecture'::'Physical Functions'::'Root Physical Function'.'Resist Front Wheels',
                    'eRod_Autonomous_Vehicle_2024 Project'::'eRod_Autonomous_Vehicle_2024'::'Physical Architecture'::'Physical Functions'::'Root Physical Function'.'Informed Software update',
                    'eRod_Autonomous_Vehicle_2024 Project'::'eRod_Autonomous_Vehicle_2024'::'Physical Architecture'::'Physical Functions'::'Root Physical Function'.'Drive vehicle',
                    'eRod_Autonomous_Vehicle_2024 Project'::'eRod_Autonomous_Vehicle_2024'::'Physical Architecture'::'Physical Functions'::'Root Physical Function'.'Detect obstacles',
                    'eRod_Autonomous_Vehicle_2024 Project'::'eRod_Autonomous_Vehicle_2024'::'Physical Architecture'::'Physical Functions'::'Root Physical Function'.'Detect intersections',
                    'eRod_Autonomous_Vehicle_2024 Project'::'eRod_Autonomous_Vehicle_2024'::'Physical Architecture'::'Physical Functions'::'Root Physical Function'.'Detect road',
                    'eRod_Autonomous_Vehicle_2024 Project'::'eRod_Autonomous_Vehicle_2024'::'Physical Architecture'::'Physical Functions'::'Root Physical Function'.'Detect signs',
                    'eRod_Autonomous_Vehicle_2024 Project'::'eRod_Autonomous_Vehicle_2024'::'Physical Architecture'::'Physical Functions'::'Root Physical Function'.'Provide weather',
                    'eRod_Autonomous_Vehicle_2024 Project'::'eRod_Autonomous_Vehicle_2024'::'Physical Architecture'::'Physical Functions'::'Root Physical Function'.'Provide road markers',
                    'eRod_Autonomous_Vehicle_2024 Project'::'eRod_Autonomous_Vehicle_2024'::'Physical Architecture'::'Physical Functions'::'Root Physical Function'.'Detect lights',
                    'eRod_Autonomous_Vehicle_2024 Project'::'eRod_Autonomous_Vehicle_2024'::'Physical Architecture'::'Physical Functions'::'Root Physical Function'.'Capture points',
                    'eRod_Autonomous_Vehicle_2024 Project'::'eRod_Autonomous_Vehicle_2024'::'Physical Architecture'::'Physical Functions'::'Root Physical Function'.'Capture radar echo',
                    'eRod_Autonomous_Vehicle_2024 Project'::'eRod_Autonomous_Vehicle_2024'::'Physical Architecture'::'Physical Functions'::'Root Physical Function'.'Avoid collision'); 
                    ref :>> ownedFunctionalExchanges =  ('eRod_Autonomous_Vehicle_2024 Project'::'eRod_Autonomous_Vehicle_2024'::'Physical Architecture'::'Physical Functions'::'Root Physical Function'.'9b4000bd-c473-4c80-a275-48cb0e12156f',
                    'eRod_Autonomous_Vehicle_2024 Project'::'eRod_Autonomous_Vehicle_2024'::'Physical Architecture'::'Physical Functions'::'Root Physical Function'.'4e03206e-6b66-41ae-9545-cc5cbb1ce6ac',
                    'eRod_Autonomous_Vehicle_2024 Project'::'eRod_Autonomous_Vehicle_2024'::'Physical Architecture'::'Physical Functions'::'Root Physical Function'.'456055aa-4b85-43b2-8567-70e2f0fad6bf',
                    'eRod_Autonomous_Vehicle_2024 Project'::'eRod_Autonomous_Vehicle_2024'::'Physical Architecture'::'Physical Functions'::'Root Physical Function'.'5c452de6-54ad-4990-a4d6-eb8f0c3acb34',
                    'eRod_Autonomous_Vehicle_2024 Project'::'eRod_Autonomous_Vehicle_2024'::'Physical Architecture'::'Physical Functions'::'Root Physical Function'.'3e32e08c-4ec4-4d11-984b-e71b9f8a7eba',
                    'eRod_Autonomous_Vehicle_2024 Project'::'eRod_Autonomous_Vehicle_2024'::'Physical Architecture'::'Physical Functions'::'Root Physical Function'.'3323da4e-ac6a-472c-8e08-4f552dc0e710',
                    'eRod_Autonomous_Vehicle_2024 Project'::'eRod_Autonomous_Vehicle_2024'::'Physical Architecture'::'Physical Functions'::'Root Physical Function'.'1bc640fb-b164-4519-b71d-d0dd4c284f64',
                    'eRod_Autonomous_Vehicle_2024 Project'::'eRod_Autonomous_Vehicle_2024'::'Physical Architecture'::'Physical Functions'::'Root Physical Function'.'dffd79cd-b8f3-416a-843c-0f9d05a57d2a',
                    'eRod_Autonomous_Vehicle_2024 Project'::'eRod_Autonomous_Vehicle_2024'::'Physical Architecture'::'Physical Functions'::'Root Physical Function'.'c4d37336-ab25-492f-b4b6-351feb813405',
                    'eRod_Autonomous_Vehicle_2024 Project'::'eRod_Autonomous_Vehicle_2024'::'Physical Architecture'::'Physical Functions'::'Root Physical Function'.'3456a6a1-0825-47fd-bafc-064d5940fc0c',
                    'eRod_Autonomous_Vehicle_2024 Project'::'eRod_Autonomous_Vehicle_2024'::'Physical Architecture'::'Physical Functions'::'Root Physical Function'.'263913cb-fa3b-4d7a-8f60-9cb9c8fb507a',
                    'eRod_Autonomous_Vehicle_2024 Project'::'eRod_Autonomous_Vehicle_2024'::'Physical Architecture'::'Physical Functions'::'Root Physical Function'.'bf906ee8-dedd-4fe1-91d5-f7853ff901ae',
                    'eRod_Autonomous_Vehicle_2024 Project'::'eRod_Autonomous_Vehicle_2024'::'Physical Architecture'::'Physical Functions'::'Root Physical Function'.'e7d77080-1205-48b7-922e-54b69ae5eb6e',
                    'eRod_Autonomous_Vehicle_2024 Project'::'eRod_Autonomous_Vehicle_2024'::'Physical Architecture'::'Physical Functions'::'Root Physical Function'.'25a019eb-1f3e-4af4-910c-1c9ec88d3bbd',
                    'eRod_Autonomous_Vehicle_2024 Project'::'eRod_Autonomous_Vehicle_2024'::'Physical Architecture'::'Physical Functions'::'Root Physical Function'.'56b5a67c-b469-4ef5-af7d-e1fb7e3bfcf5',
                    'eRod_Autonomous_Vehicle_2024 Project'::'eRod_Autonomous_Vehicle_2024'::'Physical Architecture'::'Physical Functions'::'Root Physical Function'.'7ae44802-8c02-4afc-9143-cd74794cb224',
                    'eRod_Autonomous_Vehicle_2024 Project'::'eRod_Autonomous_Vehicle_2024'::'Physical Architecture'::'Physical Functions'::'Root Physical Function'.'58863c2d-ded0-49c9-8337-1aaeec5c9015',
                    'eRod_Autonomous_Vehicle_2024 Project'::'eRod_Autonomous_Vehicle_2024'::'Physical Architecture'::'Physical Functions'::'Root Physical Function'.'4deab054-027c-43d9-bdcb-0acc6b2bbd1e',
                    'eRod_Autonomous_Vehicle_2024 Project'::'eRod_Autonomous_Vehicle_2024'::'Physical Architecture'::'Physical Functions'::'Root Physical Function'.'86db36a6-de52-4275-a1c2-d24a5d1d027e',
                    'eRod_Autonomous_Vehicle_2024 Project'::'eRod_Autonomous_Vehicle_2024'::'Physical Architecture'::'Physical Functions'::'Root Physical Function'.'e3f1fb22-0869-4f7a-af75-8be9de9dc08b',
                    'eRod_Autonomous_Vehicle_2024 Project'::'eRod_Autonomous_Vehicle_2024'::'Physical Architecture'::'Physical Functions'::'Root Physical Function'.'d355c232-2f84-4da6-88be-ea3b3e3927fd',
                    'eRod_Autonomous_Vehicle_2024 Project'::'eRod_Autonomous_Vehicle_2024'::'Physical Architecture'::'Physical Functions'::'Root Physical Function'.'f39aa588-fe27-4554-82db-26cf09846ede',
                    'eRod_Autonomous_Vehicle_2024 Project'::'eRod_Autonomous_Vehicle_2024'::'Physical Architecture'::'Physical Functions'::'Root Physical Function'.'bba22ee9-6f29-4047-a51e-4586c707a2ab',
                    'eRod_Autonomous_Vehicle_2024 Project'::'eRod_Autonomous_Vehicle_2024'::'Physical Architecture'::'Physical Functions'::'Root Physical Function'.'ee196aea-0c20-4dac-8b1c-fdcbfc3fa9b4',
                    'eRod_Autonomous_Vehicle_2024 Project'::'eRod_Autonomous_Vehicle_2024'::'Physical Architecture'::'Physical Functions'::'Root Physical Function'.'e6396c65-fc89-49bd-9e09-86f944ff82c8',
                    'eRod_Autonomous_Vehicle_2024 Project'::'eRod_Autonomous_Vehicle_2024'::'Physical Architecture'::'Physical Functions'::'Root Physical Function'.'e40e3190-0e42-4663-bfac-33ccc696d16c',
                    'eRod_Autonomous_Vehicle_2024 Project'::'eRod_Autonomous_Vehicle_2024'::'Physical Architecture'::'Physical Functions'::'Root Physical Function'.'f6baab41-8911-4e66-8f00-539758ee0712',
                    'eRod_Autonomous_Vehicle_2024 Project'::'eRod_Autonomous_Vehicle_2024'::'Physical Architecture'::'Physical Functions'::'Root Physical Function'.'d2daff82-a3d3-4886-bdb2-c577243622ec',
                    'eRod_Autonomous_Vehicle_2024 Project'::'eRod_Autonomous_Vehicle_2024'::'Physical Architecture'::'Physical Functions'::'Root Physical Function'.'958f7393-a4d1-4939-812a-e1ec2778701b',
                    'eRod_Autonomous_Vehicle_2024 Project'::'eRod_Autonomous_Vehicle_2024'::'Physical Architecture'::'Physical Functions'::'Root Physical Function'.'6b77677c-6a80-4a58-a5ea-6922399b4ff9',
                    'eRod_Autonomous_Vehicle_2024 Project'::'eRod_Autonomous_Vehicle_2024'::'Physical Architecture'::'Physical Functions'::'Root Physical Function'.'9d9dee37-2079-419b-b8a5-dd75d6999ad4',
                    'eRod_Autonomous_Vehicle_2024 Project'::'eRod_Autonomous_Vehicle_2024'::'Physical Architecture'::'Physical Functions'::'Root Physical Function'.'6852c281-c259-46c4-86e8-68298fdc0d9f',
                    'eRod_Autonomous_Vehicle_2024 Project'::'eRod_Autonomous_Vehicle_2024'::'Physical Architecture'::'Physical Functions'::'Root Physical Function'.'2e252c5d-7afb-41da-9e4d-8bdb27007357',
                    'eRod_Autonomous_Vehicle_2024 Project'::'eRod_Autonomous_Vehicle_2024'::'Physical Architecture'::'Physical Functions'::'Root Physical Function'.'e04176ef-bcbd-4847-a097-8577fdcff587',
                    'eRod_Autonomous_Vehicle_2024 Project'::'eRod_Autonomous_Vehicle_2024'::'Physical Architecture'::'Physical Functions'::'Root Physical Function'.'2e63b9b6-b395-4be2-bd4a-aef1e86e68e5',
                    'eRod_Autonomous_Vehicle_2024 Project'::'eRod_Autonomous_Vehicle_2024'::'Physical Architecture'::'Physical Functions'::'Root Physical Function'.'39b93495-b582-48da-8bb1-582aa8881fa3',
                    'eRod_Autonomous_Vehicle_2024 Project'::'eRod_Autonomous_Vehicle_2024'::'Physical Architecture'::'Physical Functions'::'Root Physical Function'.'7c524b91-a90e-4535-9f95-267c0a21af4f',
                    'eRod_Autonomous_Vehicle_2024 Project'::'eRod_Autonomous_Vehicle_2024'::'Physical Architecture'::'Physical Functions'::'Root Physical Function'.'d941a7b8-ebeb-49a0-8409-40002fac20ea',
                    'eRod_Autonomous_Vehicle_2024 Project'::'eRod_Autonomous_Vehicle_2024'::'Physical Architecture'::'Physical Functions'::'Root Physical Function'.'903bc69d-807f-4fa6-a826-db220b0dfa6d',
                    'eRod_Autonomous_Vehicle_2024 Project'::'eRod_Autonomous_Vehicle_2024'::'Physical Architecture'::'Physical Functions'::'Root Physical Function'.'0c2c6759-00c7-4f6b-a509-f44c7a2aa1dc',
                    'eRod_Autonomous_Vehicle_2024 Project'::'eRod_Autonomous_Vehicle_2024'::'Physical Architecture'::'Physical Functions'::'Root Physical Function'.'9a080694-6c18-47e9-9819-30442b7aaa82',
                    'eRod_Autonomous_Vehicle_2024 Project'::'eRod_Autonomous_Vehicle_2024'::'Physical Architecture'::'Physical Functions'::'Root Physical Function'.'0f9346cb-60f7-4f52-b116-7a5eba3ad699',
                    'eRod_Autonomous_Vehicle_2024 Project'::'eRod_Autonomous_Vehicle_2024'::'Physical Architecture'::'Physical Functions'::'Root Physical Function'.'72b2e304-b89e-4c1d-a64b-701d914c0226',
                    'eRod_Autonomous_Vehicle_2024 Project'::'eRod_Autonomous_Vehicle_2024'::'Physical Architecture'::'Physical Functions'::'Root Physical Function'.'ad5502cd-ad0e-43aa-b2d7-cf0abcd36c4e',
                    'eRod_Autonomous_Vehicle_2024 Project'::'eRod_Autonomous_Vehicle_2024'::'Physical Architecture'::'Physical Functions'::'Root Physical Function'.'31a8809d-3d03-4ca1-8898-62af332f0687',
                    'eRod_Autonomous_Vehicle_2024 Project'::'eRod_Autonomous_Vehicle_2024'::'Physical Architecture'::'Physical Functions'::'Root Physical Function'.'2b8263b6-4be5-4e78-9588-d14cbbfe6db1',
                    'eRod_Autonomous_Vehicle_2024 Project'::'eRod_Autonomous_Vehicle_2024'::'Physical Architecture'::'Physical Functions'::'Root Physical Function'.'183930ab-9da1-4de3-b265-8497bd93ce51',
                    'eRod_Autonomous_Vehicle_2024 Project'::'eRod_Autonomous_Vehicle_2024'::'Physical Architecture'::'Physical Functions'::'Root Physical Function'.'f26cc61f-55b2-40ce-b8e4-5c87c1e11692',
                    'eRod_Autonomous_Vehicle_2024 Project'::'eRod_Autonomous_Vehicle_2024'::'Physical Architecture'::'Physical Functions'::'Root Physical Function'.'4c223d18-1eaf-4293-b5bf-4d114649ab2b',
                    'eRod_Autonomous_Vehicle_2024 Project'::'eRod_Autonomous_Vehicle_2024'::'Physical Architecture'::'Physical Functions'::'Root Physical Function'.'bb3291df-08bb-4dda-bb17-582231a87c97',
                    'eRod_Autonomous_Vehicle_2024 Project'::'eRod_Autonomous_Vehicle_2024'::'Physical Architecture'::'Physical Functions'::'Root Physical Function'.'39cf23bb-f26c-40c2-a631-9155541fab5d',
                    'eRod_Autonomous_Vehicle_2024 Project'::'eRod_Autonomous_Vehicle_2024'::'Physical Architecture'::'Physical Functions'::'Root Physical Function'.'047e4a9b-a322-4c60-a6fe-15a5d26e63ed',
                    'eRod_Autonomous_Vehicle_2024 Project'::'eRod_Autonomous_Vehicle_2024'::'Physical Architecture'::'Physical Functions'::'Root Physical Function'.'d4ce739f-b313-4ee5-87fd-97676dae628f',
                    'eRod_Autonomous_Vehicle_2024 Project'::'eRod_Autonomous_Vehicle_2024'::'Physical Architecture'::'Physical Functions'::'Root Physical Function'.'74d01859-163f-413f-bb52-1b476780004a',
                    'eRod_Autonomous_Vehicle_2024 Project'::'eRod_Autonomous_Vehicle_2024'::'Physical Architecture'::'Physical Functions'::'Root Physical Function'.'150f9456-b1c3-47b1-95df-79c543bf5015',
                    'eRod_Autonomous_Vehicle_2024 Project'::'eRod_Autonomous_Vehicle_2024'::'Physical Architecture'::'Physical Functions'::'Root Physical Function'.'05bbbd1d-69e8-4e7d-bddf-c01c48911cd4'); 
                     
                }  
            } 
            package  'Interfaces' {
                @PackageMeta {
                    type = "InterfacePkg";
                } 
                @CapellaID { eid = "0267eb88-d445-4cbe-bfe3-6d0e66f73d9a"; } 
                item 'Steer Torque Interface' : InterfaceItem  { 
                    @CapellaID { eid = "f0b1d1d3-c0b0-479b-8297-786a2e034206"; } 
                    attribute :>> isAbstract = false; 
                    attribute :>> isFinal = false; 
                    attribute :>> isStructural = true; 
                    allocation '23ab2cf0-8ff6-4bba-b94f-cb876686e54d' : ExchangeItemAllocation
                        allocate allocatedItem ::> 'eRod_Autonomous_Vehicle_2024 Project'::'eRod_Autonomous_Vehicle_2024'::'Physical Architecture'::'Data'::'Steering Angle'
                        to allocatingInterface ::> 'eRod_Autonomous_Vehicle_2024 Project'::'eRod_Autonomous_Vehicle_2024'::'Physical Architecture'::'Interfaces'::'Steer Torque Interface'; 
                    allocation '3f2e50be-137a-4b45-8482-1ccbd861afd1' : ExchangeItemAllocation
                        allocate allocatedItem ::> 'eRod_Autonomous_Vehicle_2024 Project'::'eRod_Autonomous_Vehicle_2024'::'Physical Architecture'::'Data'::'Steering Force'
                        to allocatingInterface ::> 'eRod_Autonomous_Vehicle_2024 Project'::'eRod_Autonomous_Vehicle_2024'::'Physical Architecture'::'Interfaces'::'Steer Torque Interface'; 
                    ref :>> ownedExchangeItemAllocations =  ('eRod_Autonomous_Vehicle_2024 Project'::'eRod_Autonomous_Vehicle_2024'::'Physical Architecture'::'Interfaces'::'Steer Torque Interface'.'23ab2cf0-8ff6-4bba-b94f-cb876686e54d',
                    'eRod_Autonomous_Vehicle_2024 Project'::'eRod_Autonomous_Vehicle_2024'::'Physical Architecture'::'Interfaces'::'Steer Torque Interface'.'3f2e50be-137a-4b45-8482-1ccbd861afd1'); 
                     
                }  
                item 'Steering' : InterfaceItem  { 
                    @CapellaID { eid = "c6915338-4758-44a2-8e21-b545a55fbb6d"; } 
                    attribute :>> isAbstract = false; 
                    attribute :>> isFinal = false; 
                    attribute :>> isStructural = true; 
                    allocation '0dfb4f37-bd76-48cc-9422-f21e04b62a8b' : ExchangeItemAllocation
                        allocate allocatedItem ::> 'eRod_Autonomous_Vehicle_2024 Project'::'eRod_Autonomous_Vehicle_2024'::'Physical Architecture'::'Data'::'Steering Force'
                        to allocatingInterface ::> 'eRod_Autonomous_Vehicle_2024 Project'::'eRod_Autonomous_Vehicle_2024'::'Physical Architecture'::'Interfaces'::'Steering'; 
                    allocation 'a42913fd-ea43-43b3-b91c-1e9a5436058b' : ExchangeItemAllocation
                        allocate allocatedItem ::> 'eRod_Autonomous_Vehicle_2024 Project'::'eRod_Autonomous_Vehicle_2024'::'Physical Architecture'::'Data'::'Steering Angle'
                        to allocatingInterface ::> 'eRod_Autonomous_Vehicle_2024 Project'::'eRod_Autonomous_Vehicle_2024'::'Physical Architecture'::'Interfaces'::'Steering'; 
                    ref :>> ownedExchangeItemAllocations =  ('eRod_Autonomous_Vehicle_2024 Project'::'eRod_Autonomous_Vehicle_2024'::'Physical Architecture'::'Interfaces'::'Steering'.'0dfb4f37-bd76-48cc-9422-f21e04b62a8b',
                    'eRod_Autonomous_Vehicle_2024 Project'::'eRod_Autonomous_Vehicle_2024'::'Physical Architecture'::'Interfaces'::'Steering'.'a42913fd-ea43-43b3-b91c-1e9a5436058b'); 
                     
                }  
                item 'ADAS - Vector__XXX' : InterfaceItem  { 
                    @CapellaID { eid = "964e4894-d65e-4ae8-854f-3e7b22bec58c"; } 
                    attribute :>> isAbstract = false; 
                    attribute :>> isFinal = false; 
                    attribute :>> isStructural = true; 
                    allocation 'e97ea894-f132-40d5-b37a-9397c8a66f56' : ExchangeItemAllocation
                        allocate allocatedItem ::> 'eRod_Autonomous_Vehicle_2024 Project'::'eRod_Autonomous_Vehicle_2024'::'Physical Architecture'::'Data'::'ADAS'::'ADAS_ACC_Frame'
                        to allocatingInterface ::> 'eRod_Autonomous_Vehicle_2024 Project'::'eRod_Autonomous_Vehicle_2024'::'Physical Architecture'::'Interfaces'::'ADAS - Vector__XXX'; 
                    ref :>> ownedExchangeItemAllocations =  ('eRod_Autonomous_Vehicle_2024 Project'::'eRod_Autonomous_Vehicle_2024'::'Physical Architecture'::'Interfaces'::'ADAS - Vector__XXX'.'e97ea894-f132-40d5-b37a-9397c8a66f56'); 
                }  
            } 
            package  'Data' {
                @PackageMeta {
                    type = "DataPkg";
                } 
                @CapellaID { eid = "e24c3d94-ca12-4646-837d-a344176b3952"; } 
                item 'Steering Force' : ExchangeItem  { 
                    doc /*
                    According to the research conducted by Craig W. Reynolds in his seminal paper "Flocks, Herds, and Schools: A Distributed Behavioral Model," a Steering Force is a fundamental concept in the study of collective behavior and autonomous agent simulation.

                    In the context of Reynolds' boid model, a Steering Force is a vector that determines the direction and magnitude of movement for an agent (or boid) within a group. The Steering Force is composed of various components, such as cohesion, separation, and alignment forces, which work together to simulate the observed collective behaviors of flocks, herds, and schools.

                    The cohesion force acts to keep agents close together, promoting group cohesiveness. The separation force pushes agents apart to avoid collisions and maintain personal space. The alignment force aligns an agent's heading with the average heading of its neighbors, resulting in coordinated movement.

                    By combining these steering forces, Reynolds demonstrated that agents can exhibit emergent behaviors, such as flocking, schooling, and herding. This research has had significant implications not only in the field of computer graphics and animation but also in understanding collective behaviors in natural systems.

                    Reynolds, C. W. (1987). Flocks, herds and schools: A distributed behavioral model. ACM SIGGRAPH Computer Graphics, 21(4), 25-34.

                    <!--
                    Response formatted in formal HTML:

                    <!DOCTYPE html>
                    <html>
                    <head>
                        <title>Steering Force Description</title>
                    </head>
                    <body>
                        <h1>Steering Force</h1>
                        <p>According to the research conducted by Craig W. Reynolds in his seminal paper "Flocks, Herds, and Schools: A Distributed Behavioral Model," a Steering Force is a fundamental concept in the study of collective behavior and autonomous agent simulation.</p>
                        <p>In the context of Reynolds' boid model, a Steering Force is a vector that determines the direction and magnitude of movement for an agent (or boid) within a group. The Steering Force is composed of various components, such as cohesion, separation, and alignment forces, which work together to simulate the observed collective behaviors of flocks, herds, and schools.</p>
                        <p>The cohesion force acts to keep agents close together, promoting group cohesiveness. The separation force pushes agents apart to avoid collisions and maintain personal space. The alignment force aligns an agent's heading with the average heading of its neighbors, resulting in coordinated movement.</p>
                        <p>By combining these steering forces, Reynolds demonstrated that agents can exhibit emergent behaviors, such as flocking, schooling, and herding. This research has had significant implications not only in the field of computer graphics and animation but also in understanding collective behaviors in natural systems.</p>
                        <p>Reynolds, C. W. (1987). <i>Flocks, herds and schools: A distributed behavioral model.</i> ACM SIGGRAPH Computer Graphics, 21(4), 25-34.</p>
                    </body>
                    </html>
                    -->
                    */ 
                    @CapellaID { eid = "6cd5d082-6cbb-420d-82db-b0413a382cfe"; } 
                    attribute :>> isAbstract = false; 
                    attribute :>> exchangeMechanism = ExchangeMechanism::FLOW; 
                    attribute :>> isFinal = false; 
                    item 'Steering Force' : ExchangeItemElement { 
                        @CapellaID { eid = "2ec17890-0423-484d-b629-6c6a3d493b7c"; } 
                        attribute :>> isComposite = true; 
                        attribute :>> direction = ParameterDirection::UNSET; 
                        attribute :>> kind = ElementKind::TYPE; 
                        attribute :>> isMaxInclusive = false; 
                        attribute :>> isMinInclusive = false; 
                        attribute :>> isOrdered = false; 
                        attribute :>> isUnique = false; 
                         
                         
                    } 
                    ref :>> ownedElements =  ('eRod_Autonomous_Vehicle_2024 Project'::'eRod_Autonomous_Vehicle_2024'::'Physical Architecture'::'Data'::'Steering Force'.'Steering Force'); 
                }  
                item 'Steering Angle' : ExchangeItem  { 
                    doc /*
                    <style type="text/css">body {
                      font-family: Arial, sans-serif;
                    }
                    h2 {
                      color: #333333;
                    }
                    p {
                      color: #555555;
                    }
                    cite {
                      color: #777777;
                    }
                    </style>
                    <h2>Steering Angle</h2>

                    <p>A steering angle refers to the angle of rotation of the front wheels of a vehicle with respect to the vehicle&#39;s longitudinal axis. It is the angle between the direction the wheels are facing and the direction the vehicle is moving or intending to move.</p>

                    <p>The steering angle is a crucial parameter for controlling the direction of a vehicle and determining its path. It depends on various factors such as the position of the steering wheel, the steering mechanism, and the suspension geometry.</p>

                    <p>Knowing the steering angle is essential for various automotive applications, including vehicle stability control, electronic stability programs, and advanced driver-assistance systems.</p>

                    <p>&nbsp;</p>

                    */ 
                    @CapellaID { eid = "909f869c-d67e-4713-a6de-1be3431a6418"; } 
                    attribute :>> isAbstract = false; 
                    attribute :>> exchangeMechanism = ExchangeMechanism::FLOW; 
                    attribute :>> isFinal = false; 
                    item 'Steering Angle' : ExchangeItemElement { 
                        @CapellaID { eid = "3b9a7cc6-a75e-4874-8db8-219bd051ff02"; } 
                        attribute :>> isComposite = true; 
                        attribute :>> direction = ParameterDirection::UNSET; 
                        attribute :>> kind = ElementKind::TYPE; 
                        attribute :>> isMaxInclusive = false; 
                        attribute :>> isMinInclusive = false; 
                        attribute :>> isOrdered = false; 
                        attribute :>> isUnique = false; 
                         
                         
                    } 
                    ref :>> ownedElements =  ('eRod_Autonomous_Vehicle_2024 Project'::'eRod_Autonomous_Vehicle_2024'::'Physical Architecture'::'Data'::'Steering Angle'.'Steering Angle'); 
                }  
                item 'Steering Angle' : ExchangeItem  { 
                    @CapellaID { eid = "349cf8ef-2ca9-44d2-b536-60265350e72e"; } 
                    attribute :>> isAbstract = false; 
                    attribute :>> exchangeMechanism = ExchangeMechanism::SHARED_DATA; 
                    attribute :>> isFinal = false; 
                }  
                item 'Steering Force' : ExchangeItem  { 
                    @CapellaID { eid = "14e80981-4472-46aa-b6f8-bbb18cafd5df"; } 
                    attribute :>> isAbstract = false; 
                    attribute :>> exchangeMechanism = ExchangeMechanism::SHARED_DATA; 
                    attribute :>> isFinal = false; 
                }  
                package  'CAN Formatting' {
                    @PackageMeta {
                        type = "DataPkg";
                        summary = "Formatting types for CAN-based communication";
                    } 
                    @CapellaID { eid = "f38af75d-f417-4804-bc96-4e48de60dfad"; } 
                    item 'CANMessage' : Class { 
                        @CapellaID { eid = "f4ea8264-2b42-4111-92c2-23bfe3067500"; } 
                        attribute :>> isAbstract = false; 
                        attribute :>> isFinal = false; 
                        attribute :>> isPrimitive = false; 
                    }  
                    item 'CANSignal' : Class { 
                        @CapellaID { eid = "0b34c62c-82ed-4916-a21a-9ec0286ece78"; } 
                        attribute :>> isAbstract = false; 
                        attribute :>> isFinal = false; 
                        attribute :>> isPrimitive = false; 
                    }  
                } 
                package  'ADAS' {
                    @PackageMeta {
                        type = "DataPkg";
                    } 
                    @CapellaID { eid = "dd5c5d88-9f03-41fd-b1be-7e4ad727f349"; } 
                    item 'ADAS_ACC_Frame' : ExchangeItem  { 
                        @CapellaID { eid = "ee0894c3-f04c-4b61-9269-8690eeb36809"; } 
                        attribute :>> isAbstract = false; 
                        attribute :>> exchangeMechanism = ExchangeMechanism::EVENT; 
                        attribute :>> isFinal = false; 
                        item 'ADAS_ACC_Frame' : ExchangeItemElement { 
                            @CapellaID { eid = "25ef7778-d9d8-4458-897b-e2404a47f28f"; } 
                            attribute :>> isComposite = false; 
                            attribute :>> direction = ParameterDirection::UNSET; 
                            attribute :>> kind = ElementKind::TYPE; 
                            attribute :>> isMaxInclusive = false; 
                            attribute :>> isMinInclusive = false; 
                            attribute :>> isOrdered = false; 
                            attribute :>> isUnique = false; 
                            attribute 'Definition' : PropertyValueGroup { 
                                @CapellaID { eid = "e80b0b80-5bf0-43a1-bac1-80b60e4bad64"; } 
                                attribute 'DLC' : IntegerPropertyValue  = 8 { 
                                    @CapellaID { eid = "84a70b5c-e0ed-41ab-bfa7-bd02b782b899"; } 
                                }  
                                attribute 'Cycle_Time' : IntegerPropertyValue  = 10 { 
                                    @CapellaID { eid = "be531c0c-c6c6-4e77-843f-103c2b50bf57"; } 
                                }  
                                attribute 'Type' : StringPropertyValue  = 'CAN Standard' { 
                                    @CapellaID { eid = "43d3e427-4f77-4e9b-80f2-dc8dda5aa55a"; } 
                                }  
                                ref :>> ownedPropertyValues =  ('eRod_Autonomous_Vehicle_2024 Project'::'eRod_Autonomous_Vehicle_2024'::'Physical Architecture'::'Data'::'ADAS'::'ADAS_ACC_Frame'.'ADAS_ACC_Frame'.'Definition'.'DLC',
                                'eRod_Autonomous_Vehicle_2024 Project'::'eRod_Autonomous_Vehicle_2024'::'Physical Architecture'::'Data'::'ADAS'::'ADAS_ACC_Frame'.'ADAS_ACC_Frame'.'Definition'.'Cycle_Time',
                                'eRod_Autonomous_Vehicle_2024 Project'::'eRod_Autonomous_Vehicle_2024'::'Physical Architecture'::'Data'::'ADAS'::'ADAS_ACC_Frame'.'ADAS_ACC_Frame'.'Definition'.'Type'); 
                            }  
                            attribute 'Attributes' : PropertyValueGroup { 
                                @CapellaID { eid = "840d860d-69fa-4ecb-a259-765f651a231c"; } 
                                attribute 'GenMsgCycleTime' : StringPropertyValue  = '10.000' { 
                                    @CapellaID { eid = "5ec6f5b1-9f39-47e1-a3cf-b0c5f33475ec"; } 
                                }  
                                attribute 'GenMsgSendType' : StringPropertyValue  = 'cyclic' { 
                                    @CapellaID { eid = "44e6692f-8fab-44cd-bf5c-e99350d5f0a1"; } 
                                }  
                                attribute 'GenMsgStartDelayTime' : StringPropertyValue  = '0.000' { 
                                    @CapellaID { eid = "2f8f2a20-1474-44fe-824a-2f98a709ff33"; } 
                                }  
                                ref :>> ownedPropertyValues =  ('eRod_Autonomous_Vehicle_2024 Project'::'eRod_Autonomous_Vehicle_2024'::'Physical Architecture'::'Data'::'ADAS'::'ADAS_ACC_Frame'.'ADAS_ACC_Frame'.'Attributes'.'GenMsgCycleTime',
                                'eRod_Autonomous_Vehicle_2024 Project'::'eRod_Autonomous_Vehicle_2024'::'Physical Architecture'::'Data'::'ADAS'::'ADAS_ACC_Frame'.'ADAS_ACC_Frame'.'Attributes'.'GenMsgSendType',
                                'eRod_Autonomous_Vehicle_2024 Project'::'eRod_Autonomous_Vehicle_2024'::'Physical Architecture'::'Data'::'ADAS'::'ADAS_ACC_Frame'.'ADAS_ACC_Frame'.'Attributes'.'GenMsgStartDelayTime'); 
                            }  
                             
                             
                            ref :>> appliedPropertyValueGroups =  ('eRod_Autonomous_Vehicle_2024 Project'::'eRod_Autonomous_Vehicle_2024'::'Physical Architecture'::'Data'::'ADAS'::'ADAS_ACC_Frame'.'ADAS_ACC_Frame'.'Definition',
                            'eRod_Autonomous_Vehicle_2024 Project'::'eRod_Autonomous_Vehicle_2024'::'Physical Architecture'::'Data'::'ADAS'::'ADAS_ACC_Frame'.'ADAS_ACC_Frame'.'Attributes'); 
                            ref :>> ownedPropertyValueGroups =  ('eRod_Autonomous_Vehicle_2024 Project'::'eRod_Autonomous_Vehicle_2024'::'Physical Architecture'::'Data'::'ADAS'::'ADAS_ACC_Frame'.'ADAS_ACC_Frame'.'Definition',
                            'eRod_Autonomous_Vehicle_2024 Project'::'eRod_Autonomous_Vehicle_2024'::'Physical Architecture'::'Data'::'ADAS'::'ADAS_ACC_Frame'.'ADAS_ACC_Frame'.'Attributes'); 
                            ref :>> abstractType = 'eRod_Autonomous_Vehicle_2024 Project'::'eRod_Autonomous_Vehicle_2024'::'Physical Architecture'::'Data'::'CAN Formatting'::'CANMessage';
                        } 
                        item 'BrakeSwitch3' : ExchangeItemElement { 
                            @CapellaID { eid = "f50f019e-3791-413a-932f-90acad03ab89"; } 
                            attribute :>> isComposite = false; 
                            attribute :>> direction = ParameterDirection::UNSET; 
                            attribute :>> kind = ElementKind::TYPE; 
                            attribute :>> isMaxInclusive = false; 
                            attribute :>> isMinInclusive = false; 
                            attribute :>> isOrdered = false; 
                            attribute :>> isUnique = false; 
                            attribute 'Definition' : PropertyValueGroup { 
                                @CapellaID { eid = "15a4ff32-88b7-43da-879c-0c67bd007a1b"; } 
                                attribute 'Start_Bit' : IntegerPropertyValue  = 0 { 
                                    @CapellaID { eid = "27cd9a5d-7e53-43b6-9cd9-b04e7a77acb4"; } 
                                }  
                                attribute 'Size' : IntegerPropertyValue  = 5 { 
                                    @CapellaID { eid = "b47e6260-8f19-42fa-8226-9e1a637ed585"; } 
                                }  
                                attribute 'Factor' : FloatPropertyValue  = 1.0 { 
                                    @CapellaID { eid = "7b4b689d-91fc-42d3-b70f-ebaa131f15f2"; } 
                                }  
                                attribute 'Offset' : FloatPropertyValue  = 0.0 { 
                                    @CapellaID { eid = "d99baa4d-cb85-4d40-8882-a0150d2e00b8"; } 
                                }  
                                attribute 'Minimum' : FloatPropertyValue  = 0.0 { 
                                    @CapellaID { eid = "4c837c43-91d1-43ab-897c-62e1984dd2a2"; } 
                                }  
                                attribute 'Maximum' : FloatPropertyValue  = 31.0 { 
                                    @CapellaID { eid = "a66c4803-ae11-49ba-9c12-214dcb22b813"; } 
                                }  
                                attribute 'Unit' : StringPropertyValue  { 
                                    @CapellaID { eid = "0c6d07c8-287a-4144-ae37-ae4d473ba65d"; } 
                                }  
                                attribute 'Is Signed' : BooleanPropertyValue  = false { 
                                    @CapellaID { eid = "d2a0785f-2ca9-4fe0-9329-c34f3bd76415"; } 
                                }  
                                ref :>> ownedPropertyValues =  ('eRod_Autonomous_Vehicle_2024 Project'::'eRod_Autonomous_Vehicle_2024'::'Physical Architecture'::'Data'::'ADAS'::'ADAS_ACC_Frame'.'BrakeSwitch3'.'Definition'.'Start_Bit',
                                'eRod_Autonomous_Vehicle_2024 Project'::'eRod_Autonomous_Vehicle_2024'::'Physical Architecture'::'Data'::'ADAS'::'ADAS_ACC_Frame'.'BrakeSwitch3'.'Definition'.'Size',
                                'eRod_Autonomous_Vehicle_2024 Project'::'eRod_Autonomous_Vehicle_2024'::'Physical Architecture'::'Data'::'ADAS'::'ADAS_ACC_Frame'.'BrakeSwitch3'.'Definition'.'Factor',
                                'eRod_Autonomous_Vehicle_2024 Project'::'eRod_Autonomous_Vehicle_2024'::'Physical Architecture'::'Data'::'ADAS'::'ADAS_ACC_Frame'.'BrakeSwitch3'.'Definition'.'Offset',
                                'eRod_Autonomous_Vehicle_2024 Project'::'eRod_Autonomous_Vehicle_2024'::'Physical Architecture'::'Data'::'ADAS'::'ADAS_ACC_Frame'.'BrakeSwitch3'.'Definition'.'Minimum',
                                'eRod_Autonomous_Vehicle_2024 Project'::'eRod_Autonomous_Vehicle_2024'::'Physical Architecture'::'Data'::'ADAS'::'ADAS_ACC_Frame'.'BrakeSwitch3'.'Definition'.'Maximum',
                                'eRod_Autonomous_Vehicle_2024 Project'::'eRod_Autonomous_Vehicle_2024'::'Physical Architecture'::'Data'::'ADAS'::'ADAS_ACC_Frame'.'BrakeSwitch3'.'Definition'.'Unit',
                                'eRod_Autonomous_Vehicle_2024 Project'::'eRod_Autonomous_Vehicle_2024'::'Physical Architecture'::'Data'::'ADAS'::'ADAS_ACC_Frame'.'BrakeSwitch3'.'Definition'.'Is Signed'); 
                            }  
                            attribute 'Attributes' : PropertyValueGroup { 
                                @CapellaID { eid = "8f1429a0-298d-4331-b43f-95f07761fcc2"; } 
                                attribute 'GenSigStartValue' : StringPropertyValue  = '0' { 
                                    @CapellaID { eid = "08e4b708-6935-4d04-820d-c1f030f3d6be"; } 
                                }  
                                ref :>> ownedPropertyValues =  ('eRod_Autonomous_Vehicle_2024 Project'::'eRod_Autonomous_Vehicle_2024'::'Physical Architecture'::'Data'::'ADAS'::'ADAS_ACC_Frame'.'BrakeSwitch3'.'Attributes'.'GenSigStartValue'); 
                            }  
                             
                             
                            ref :>> appliedPropertyValueGroups =  ('eRod_Autonomous_Vehicle_2024 Project'::'eRod_Autonomous_Vehicle_2024'::'Physical Architecture'::'Data'::'ADAS'::'ADAS_ACC_Frame'.'BrakeSwitch3'.'Definition',
                            'eRod_Autonomous_Vehicle_2024 Project'::'eRod_Autonomous_Vehicle_2024'::'Physical Architecture'::'Data'::'ADAS'::'ADAS_ACC_Frame'.'BrakeSwitch3'.'Attributes'); 
                            ref :>> ownedPropertyValueGroups =  ('eRod_Autonomous_Vehicle_2024 Project'::'eRod_Autonomous_Vehicle_2024'::'Physical Architecture'::'Data'::'ADAS'::'ADAS_ACC_Frame'.'BrakeSwitch3'.'Definition',
                            'eRod_Autonomous_Vehicle_2024 Project'::'eRod_Autonomous_Vehicle_2024'::'Physical Architecture'::'Data'::'ADAS'::'ADAS_ACC_Frame'.'BrakeSwitch3'.'Attributes'); 
                            ref :>> abstractType = 'eRod_Autonomous_Vehicle_2024 Project'::'eRod_Autonomous_Vehicle_2024'::'Physical Architecture'::'Data'::'CAN Formatting'::'CANSignal';
                        } 
                        item 'MaintainDistance' : ExchangeItemElement { 
                            @CapellaID { eid = "b97f2461-e015-4b3c-8509-680caed64344"; } 
                            attribute :>> isComposite = false; 
                            attribute :>> direction = ParameterDirection::UNSET; 
                            attribute :>> kind = ElementKind::TYPE; 
                            attribute :>> isMaxInclusive = false; 
                            attribute :>> isMinInclusive = false; 
                            attribute :>> isOrdered = false; 
                            attribute :>> isUnique = false; 
                            attribute 'Definition' : PropertyValueGroup { 
                                @CapellaID { eid = "c7264f16-96bb-42e7-9fc3-fc54ccffae2f"; } 
                                attribute 'Start_Bit' : IntegerPropertyValue  = 5 { 
                                    @CapellaID { eid = "1e69e6c7-7b34-4836-832e-2ef8f254599e"; } 
                                }  
                                attribute 'Size' : IntegerPropertyValue  = 5 { 
                                    @CapellaID { eid = "418595f1-e7c1-4e0c-b22f-9642a0442529"; } 
                                }  
                                attribute 'Factor' : FloatPropertyValue  = 1.0 { 
                                    @CapellaID { eid = "21724731-88aa-466b-b2c4-d3816de0a92a"; } 
                                }  
                                attribute 'Offset' : FloatPropertyValue  = 0.0 { 
                                    @CapellaID { eid = "e1799f55-e8f8-458e-bcc5-374387de26ee"; } 
                                }  
                                attribute 'Minimum' : FloatPropertyValue  = 0.0 { 
                                    @CapellaID { eid = "52ee4267-7030-43e0-aa76-ff34c96af06f"; } 
                                }  
                                attribute 'Maximum' : FloatPropertyValue  = 31.0 { 
                                    @CapellaID { eid = "231ae408-e231-42a5-a318-837649641ba0"; } 
                                }  
                                attribute 'Unit' : StringPropertyValue  { 
                                    @CapellaID { eid = "4693e559-6c5f-470c-9d68-444ca72e552e"; } 
                                }  
                                attribute 'Is Signed' : BooleanPropertyValue  = false { 
                                    @CapellaID { eid = "6cf43845-3140-4262-8a39-c5f3c701eb87"; } 
                                }  
                                ref :>> ownedPropertyValues =  ('eRod_Autonomous_Vehicle_2024 Project'::'eRod_Autonomous_Vehicle_2024'::'Physical Architecture'::'Data'::'ADAS'::'ADAS_ACC_Frame'.'MaintainDistance'.'Definition'.'Start_Bit',
                                'eRod_Autonomous_Vehicle_2024 Project'::'eRod_Autonomous_Vehicle_2024'::'Physical Architecture'::'Data'::'ADAS'::'ADAS_ACC_Frame'.'MaintainDistance'.'Definition'.'Size',
                                'eRod_Autonomous_Vehicle_2024 Project'::'eRod_Autonomous_Vehicle_2024'::'Physical Architecture'::'Data'::'ADAS'::'ADAS_ACC_Frame'.'MaintainDistance'.'Definition'.'Factor',
                                'eRod_Autonomous_Vehicle_2024 Project'::'eRod_Autonomous_Vehicle_2024'::'Physical Architecture'::'Data'::'ADAS'::'ADAS_ACC_Frame'.'MaintainDistance'.'Definition'.'Offset',
                                'eRod_Autonomous_Vehicle_2024 Project'::'eRod_Autonomous_Vehicle_2024'::'Physical Architecture'::'Data'::'ADAS'::'ADAS_ACC_Frame'.'MaintainDistance'.'Definition'.'Minimum',
                                'eRod_Autonomous_Vehicle_2024 Project'::'eRod_Autonomous_Vehicle_2024'::'Physical Architecture'::'Data'::'ADAS'::'ADAS_ACC_Frame'.'MaintainDistance'.'Definition'.'Maximum',
                                'eRod_Autonomous_Vehicle_2024 Project'::'eRod_Autonomous_Vehicle_2024'::'Physical Architecture'::'Data'::'ADAS'::'ADAS_ACC_Frame'.'MaintainDistance'.'Definition'.'Unit',
                                'eRod_Autonomous_Vehicle_2024 Project'::'eRod_Autonomous_Vehicle_2024'::'Physical Architecture'::'Data'::'ADAS'::'ADAS_ACC_Frame'.'MaintainDistance'.'Definition'.'Is Signed'); 
                            }  
                            attribute 'Attributes' : PropertyValueGroup { 
                                @CapellaID { eid = "1d613aba-6311-4c8e-9576-308275ad6e15"; } 
                                attribute 'GenSigStartValue' : StringPropertyValue  = '0' { 
                                    @CapellaID { eid = "29c38252-a435-4284-8a8b-979cf317e280"; } 
                                }  
                                ref :>> ownedPropertyValues =  ('eRod_Autonomous_Vehicle_2024 Project'::'eRod_Autonomous_Vehicle_2024'::'Physical Architecture'::'Data'::'ADAS'::'ADAS_ACC_Frame'.'MaintainDistance'.'Attributes'.'GenSigStartValue'); 
                            }  
                             
                             
                            ref :>> appliedPropertyValueGroups =  ('eRod_Autonomous_Vehicle_2024 Project'::'eRod_Autonomous_Vehicle_2024'::'Physical Architecture'::'Data'::'ADAS'::'ADAS_ACC_Frame'.'MaintainDistance'.'Definition',
                            'eRod_Autonomous_Vehicle_2024 Project'::'eRod_Autonomous_Vehicle_2024'::'Physical Architecture'::'Data'::'ADAS'::'ADAS_ACC_Frame'.'MaintainDistance'.'Attributes'); 
                            ref :>> ownedPropertyValueGroups =  ('eRod_Autonomous_Vehicle_2024 Project'::'eRod_Autonomous_Vehicle_2024'::'Physical Architecture'::'Data'::'ADAS'::'ADAS_ACC_Frame'.'MaintainDistance'.'Definition',
                            'eRod_Autonomous_Vehicle_2024 Project'::'eRod_Autonomous_Vehicle_2024'::'Physical Architecture'::'Data'::'ADAS'::'ADAS_ACC_Frame'.'MaintainDistance'.'Attributes'); 
                            ref :>> abstractType = 'eRod_Autonomous_Vehicle_2024 Project'::'eRod_Autonomous_Vehicle_2024'::'Physical Architecture'::'Data'::'CAN Formatting'::'CANSignal';
                        } 
                        ref :>> ownedElements =  ('eRod_Autonomous_Vehicle_2024 Project'::'eRod_Autonomous_Vehicle_2024'::'Physical Architecture'::'Data'::'ADAS'::'ADAS_ACC_Frame'.'ADAS_ACC_Frame',
                        'eRod_Autonomous_Vehicle_2024 Project'::'eRod_Autonomous_Vehicle_2024'::'Physical Architecture'::'Data'::'ADAS'::'ADAS_ACC_Frame'.'BrakeSwitch3',
                        'eRod_Autonomous_Vehicle_2024 Project'::'eRod_Autonomous_Vehicle_2024'::'Physical Architecture'::'Data'::'ADAS'::'ADAS_ACC_Frame'.'MaintainDistance'); 
                    }  
                } 
            } 
            package  'Capabilities' {
                @PackageMeta {
                    type = "CapabilityRealizationPkg";
                } 
                @CapellaID { eid = "bbb3428a-e91f-40bb-80b7-e3fb8c80c792"; } 
                use case 'Sporty drive' : CapabilityRealization { 
                    @CapellaID { eid = "31d3eae6-96f9-4c75-b7c7-6d5031dec67f"; } 
                    ref action 'c346c524-220d-4326-97cc-8be2d49ed948' = 'eRod_Autonomous_Vehicle_2024 Project'::'eRod_Autonomous_Vehicle_2024'::'Physical Architecture'::'Physical Functions'::'Root Physical Function'.'Vehicle Steering'; 
                     
                     
                }  
                use case 'Autonmous Driving' : CapabilityRealization { 
                    @CapellaID { eid = "983a51ff-276d-4cea-8b84-290deba3e66b"; } 
                    ref action '335fac03-8df7-40da-9bec-d95c44069417' = 'eRod_Autonomous_Vehicle_2024 Project'::'eRod_Autonomous_Vehicle_2024'::'Physical Architecture'::'Physical Functions'::'Root Physical Function'.'Lane Keep Assist (LKA)'; 
                     
                     
                }  
                use case 'Lane Keeping Assistant (LKA)' : CapabilityRealization { 
                    @CapellaID { eid = "f965ba4f-db86-40de-b120-47228ca5cb10"; } 
                    ref action 'faf61359-c1c6-4332-a82c-e0c6fc006111' = 'eRod_Autonomous_Vehicle_2024 Project'::'eRod_Autonomous_Vehicle_2024'::'Physical Architecture'::'Physical Functions'::'Root Physical Function'.'Lane Keep Assist (LKA)'; 
                     
                     
                }  
            } 
            package  'Structure' {
                @PackageMeta {
                    type = "PhysicalComponentPkg";
                } 
                @CapellaID { eid = "8acaf3a1-6329-414b-a2a1-1e6ead84ef6b"; } 
                part 'Environment' : PhysicalComponent { 
                    @CapellaID { eid = "0525fbf9-4c55-4761-977f-b13229d518c9"; } 
                    attribute :>> isAbstract = false; 
                    attribute :>> isActor = true; 
                    attribute :>> isHuman = false; 
                    attribute :>> kind = PhysicalComponentKind::UNSET; 
                    attribute :>> nature = PhysicalComponentNature::NODE; 
                    part 'Terrain/Roads' : PhysicalComponent { 
                        @CapellaID { eid = "0cef5e53-0eb2-480b-9cbf-b42123c4827b"; } 
                        attribute :>> isAbstract = false; 
                        attribute :>> isActor = true; 
                        attribute :>> isHuman = false; 
                        attribute :>> kind = PhysicalComponentKind::UNSET; 
                        attribute :>> nature = PhysicalComponentNature::NODE; 
                        allocation '2e818d7f-bcf1-4f8b-9a77-6ba1e46267af' : ComponentFunctionalAllocation
                            allocate function ::> 'eRod_Autonomous_Vehicle_2024 Project'::'eRod_Autonomous_Vehicle_2024'::'Physical Architecture'::'Physical Functions'::'Root Physical Function'.'Provide diverse terrain'
                            to component ::> 'eRod_Autonomous_Vehicle_2024 Project'::'eRod_Autonomous_Vehicle_2024'::'Physical Architecture'::'Structure'::'Environment'.'Terrain/Roads';
                        perform 'eRod_Autonomous_Vehicle_2024 Project'::'eRod_Autonomous_Vehicle_2024'::'Physical Architecture'::'Physical Functions'::'Root Physical Function'.'Provide diverse terrain' ; 
                        allocation '1cd0af28-7263-4019-ae32-a760c776f128' : ComponentFunctionalAllocation
                            allocate function ::> 'eRod_Autonomous_Vehicle_2024 Project'::'eRod_Autonomous_Vehicle_2024'::'Physical Architecture'::'Physical Functions'::'Root Physical Function'.'Provide road markers'
                            to component ::> 'eRod_Autonomous_Vehicle_2024 Project'::'eRod_Autonomous_Vehicle_2024'::'Physical Architecture'::'Structure'::'Environment'.'Terrain/Roads';
                        perform 'eRod_Autonomous_Vehicle_2024 Project'::'eRod_Autonomous_Vehicle_2024'::'Physical Architecture'::'Physical Functions'::'Root Physical Function'.'Provide road markers' ; 
                        allocation 'd57d74af-2035-4ecb-9561-5e9c5d24d1a1' : ComponentFunctionalAllocation
                            allocate function ::> 'eRod_Autonomous_Vehicle_2024 Project'::'eRod_Autonomous_Vehicle_2024'::'Physical Architecture'::'Physical Functions'::'Root Physical Function'.'Resist Front Wheels'
                            to component ::> 'eRod_Autonomous_Vehicle_2024 Project'::'eRod_Autonomous_Vehicle_2024'::'Physical Architecture'::'Structure'::'Environment'.'Terrain/Roads';
                        perform 'eRod_Autonomous_Vehicle_2024 Project'::'eRod_Autonomous_Vehicle_2024'::'Physical Architecture'::'Physical Functions'::'Root Physical Function'.'Resist Front Wheels' ; 
                        port 'PP 1' : PhysicalPort { 
                            @CapellaID { eid = "e7500ae9-baf1-4ac9-8437-8111d8c8f761"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '12d0b90f-7a85-4e03-b135-f4081ad5b99b' : ComponentPortAllocation
                                allocate allocatedPort ::> 'eRod_Autonomous_Vehicle_2024 Project'::'eRod_Autonomous_Vehicle_2024'::'Physical Architecture'::'Structure'::'Environment'.'Terrain/Roads'.'PP 1'
                                to allocatingPort ::> 'eRod_Autonomous_Vehicle_2024 Project'::'eRod_Autonomous_Vehicle_2024'::'Physical Architecture'::'Structure'::'Environment'.'Terrain/Roads'.'CP 4'; 
                            ref :>> ownedComponentPortAllocations =  ('eRod_Autonomous_Vehicle_2024 Project'::'eRod_Autonomous_Vehicle_2024'::'Physical Architecture'::'Structure'::'Environment'.'Terrain/Roads'.'PP 1'.'12d0b90f-7a85-4e03-b135-f4081ad5b99b'); 
                        }  
                        port 'PP 2' : PhysicalPort { 
                            @CapellaID { eid = "a069f946-981a-4636-b6bd-da6fdf257216"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '20b20523-6182-49f8-b90c-29bbd24e59eb' : ComponentPortAllocation
                                allocate allocatedPort ::> 'eRod_Autonomous_Vehicle_2024 Project'::'eRod_Autonomous_Vehicle_2024'::'Physical Architecture'::'Structure'::'Environment'.'Terrain/Roads'.'PP 2'
                                to allocatingPort ::> 'eRod_Autonomous_Vehicle_2024 Project'::'eRod_Autonomous_Vehicle_2024'::'Physical Architecture'::'Structure'::'Environment'.'Terrain/Roads'.'CP 3'; 
                            ref :>> ownedComponentPortAllocations =  ('eRod_Autonomous_Vehicle_2024 Project'::'eRod_Autonomous_Vehicle_2024'::'Physical Architecture'::'Structure'::'Environment'.'Terrain/Roads'.'PP 2'.'20b20523-6182-49f8-b90c-29bbd24e59eb'); 
                        }  
                        port 'CP 3' : ComponentPort { 
                            @CapellaID { eid = "43be03ef-343f-414e-b8e7-7d0631f79780"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                            ref allocation 'da6d7576-5b6c-4eed-b17b-35857cef7b37' : PortAllocation
                                allocate allocatedPort ::> 'eRod_Autonomous_Vehicle_2024 Project'::'eRod_Autonomous_Vehicle_2024'::'Physical Architecture'::'Physical Functions'::'Root Physical Function'.'Resist Front Wheels'.'FIP 1'
                                to allocatingPort ::> 'eRod_Autonomous_Vehicle_2024 Project'::'eRod_Autonomous_Vehicle_2024'::'Physical Architecture'::'Structure'::'Environment'.'Terrain/Roads'.'CP 3'; 
                            ref :>> ownedPortAllocations =  ('eRod_Autonomous_Vehicle_2024 Project'::'eRod_Autonomous_Vehicle_2024'::'Physical Architecture'::'Structure'::'Environment'.'Terrain/Roads'.'CP 3'.'da6d7576-5b6c-4eed-b17b-35857cef7b37'); 
                        }  
                        port 'CP 4' : ComponentPort { 
                            @CapellaID { eid = "c1f9f080-7d2b-4036-a65d-b965ae5ae67d"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                            ref allocation 'a91111f7-bd97-45d0-96bb-e1e2f4d994ab' : PortAllocation
                                allocate allocatedPort ::> 'eRod_Autonomous_Vehicle_2024 Project'::'eRod_Autonomous_Vehicle_2024'::'Physical Architecture'::'Physical Functions'::'Root Physical Function'.'Resist Front Wheels'.'FIP 1'
                                to allocatingPort ::> 'eRod_Autonomous_Vehicle_2024 Project'::'eRod_Autonomous_Vehicle_2024'::'Physical Architecture'::'Structure'::'Environment'.'Terrain/Roads'.'CP 4'; 
                            ref :>> ownedPortAllocations =  ('eRod_Autonomous_Vehicle_2024 Project'::'eRod_Autonomous_Vehicle_2024'::'Physical Architecture'::'Structure'::'Environment'.'Terrain/Roads'.'CP 4'.'a91111f7-bd97-45d0-96bb-e1e2f4d994ab'); 
                        }  
                        ref :>> ownedFunctionalAllocation =  ('eRod_Autonomous_Vehicle_2024 Project'::'eRod_Autonomous_Vehicle_2024'::'Physical Architecture'::'Structure'::'Environment'.'Terrain/Roads'.'2e818d7f-bcf1-4f8b-9a77-6ba1e46267af',
                        'eRod_Autonomous_Vehicle_2024 Project'::'eRod_Autonomous_Vehicle_2024'::'Physical Architecture'::'Structure'::'Environment'.'Terrain/Roads'.'1cd0af28-7263-4019-ae32-a760c776f128',
                        'eRod_Autonomous_Vehicle_2024 Project'::'eRod_Autonomous_Vehicle_2024'::'Physical Architecture'::'Structure'::'Environment'.'Terrain/Roads'.'d57d74af-2035-4ecb-9561-5e9c5d24d1a1'); 
                         
                         
                    }  
                    part 'Weather' : PhysicalComponent { 
                        @CapellaID { eid = "61f42d07-457d-4b08-bb0f-4d2fbca79007"; } 
                        attribute :>> isAbstract = false; 
                        attribute :>> isActor = true; 
                        attribute :>> isHuman = false; 
                        attribute :>> kind = PhysicalComponentKind::UNSET; 
                        attribute :>> nature = PhysicalComponentNature::NODE; 
                        allocation '80ba73e2-8aaf-48fe-af58-b6822b88a0de' : ComponentFunctionalAllocation
                            allocate function ::> 'eRod_Autonomous_Vehicle_2024 Project'::'eRod_Autonomous_Vehicle_2024'::'Physical Architecture'::'Physical Functions'::'Root Physical Function'.'Provide weather'
                            to component ::> 'eRod_Autonomous_Vehicle_2024 Project'::'eRod_Autonomous_Vehicle_2024'::'Physical Architecture'::'Structure'::'Environment'.'Weather';
                        perform 'eRod_Autonomous_Vehicle_2024 Project'::'eRod_Autonomous_Vehicle_2024'::'Physical Architecture'::'Physical Functions'::'Root Physical Function'.'Provide weather' ; 
                        ref :>> ownedFunctionalAllocation =  ('eRod_Autonomous_Vehicle_2024 Project'::'eRod_Autonomous_Vehicle_2024'::'Physical Architecture'::'Structure'::'Environment'.'Weather'.'80ba73e2-8aaf-48fe-af58-b6822b88a0de'); 
                         
                         
                    }  
                    part 'External' : PhysicalComponent { 
                        @CapellaID { eid = "05668387-3cf5-4f50-82b9-46e915de7281"; } 
                        attribute :>> isAbstract = false; 
                        attribute :>> isActor = true; 
                        attribute :>> isHuman = false; 
                        attribute :>> kind = PhysicalComponentKind::UNSET; 
                        attribute :>> nature = PhysicalComponentNature::NODE; 
                        allocation '5b279a38-6b40-4713-bc43-dee8f78324be' : ComponentFunctionalAllocation
                            allocate function ::> 'eRod_Autonomous_Vehicle_2024 Project'::'eRod_Autonomous_Vehicle_2024'::'Physical Architecture'::'Physical Functions'::'Root Physical Function'.'Reflect lights'
                            to component ::> 'eRod_Autonomous_Vehicle_2024 Project'::'eRod_Autonomous_Vehicle_2024'::'Physical Architecture'::'Structure'::'Environment'.'External';
                        perform 'eRod_Autonomous_Vehicle_2024 Project'::'eRod_Autonomous_Vehicle_2024'::'Physical Architecture'::'Physical Functions'::'Root Physical Function'.'Reflect lights' ; 
                        ref :>> ownedFunctionalAllocation =  ('eRod_Autonomous_Vehicle_2024 Project'::'eRod_Autonomous_Vehicle_2024'::'Physical Architecture'::'Structure'::'Environment'.'External'.'5b279a38-6b40-4713-bc43-dee8f78324be'); 
                         
                         
                    }  
                    port 'CP 1' : ComponentPort { 
                        @CapellaID { eid = "a7ff5007-3434-4c48-a48f-fdd97511dd78"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                         
                    }  
                    port 'CP 2' : ComponentPort { 
                        @CapellaID { eid = "abbceb31-b592-42b2-bb4c-f6df28bf6aec"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                         
                    }  
                    port 'Environment from Motor' : ComponentPort { 
                        @CapellaID { eid = "1473a43e-a377-4fcb-85e7-1bf2aab08b12"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                        ref :>> requiredInterfaces =  ('eRod_Autonomous_Vehicle_2024 Project'::'eRod_Autonomous_Vehicle_2024'::'Logical Architecture'::'Interfaces'::'Heat'); 
                         
                    }  
                    ref :>> ownedPhysicalComponents =  ('eRod_Autonomous_Vehicle_2024 Project'::'eRod_Autonomous_Vehicle_2024'::'Physical Architecture'::'Structure'::'Environment'.'Terrain/Roads',
                    'eRod_Autonomous_Vehicle_2024 Project'::'eRod_Autonomous_Vehicle_2024'::'Physical Architecture'::'Structure'::'Environment'.'Weather',
                    'eRod_Autonomous_Vehicle_2024 Project'::'eRod_Autonomous_Vehicle_2024'::'Physical Architecture'::'Structure'::'Environment'.'External'); 
                     
                     
                }  
                part 'Physical System' : PhysicalComponent { 
                    @CapellaID { eid = "a4c31399-3c16-4191-98c5-b66847b3879b"; } 
                    attribute :>> isAbstract = false; 
                    attribute :>> isActor = false; 
                    attribute :>> isHuman = false; 
                    attribute :>> kind = PhysicalComponentKind::UNSET; 
                    attribute :>> nature = PhysicalComponentNature::UNSET; 
                    part 'eRod' : PhysicalComponent { 
                        @CapellaID { eid = "37564188-ab8b-4d1d-8187-ec9f7e63d786"; } 
                        attribute :>> isAbstract = false; 
                        attribute :>> isActor = false; 
                        attribute :>> isHuman = false; 
                        attribute :>> kind = PhysicalComponentKind::HARDWARE; 
                        attribute :>> nature = PhysicalComponentNature::NODE; 
                        part 'Power Train' : PhysicalComponent { 
                            @CapellaID { eid = "73b01491-38eb-4c77-94c0-36f86fa72dc3"; } 
                            attribute :>> isAbstract = false; 
                            attribute :>> isActor = false; 
                            attribute :>> isHuman = false; 
                            attribute :>> kind = PhysicalComponentKind::UNSET; 
                            attribute :>> nature = PhysicalComponentNature::NODE; 
                            part 'Electrical Motor' : PhysicalComponent { 
                                @CapellaID { eid = "7e5826f1-731a-4649-9395-90986d653f71"; } 
                                attribute :>> isAbstract = false; 
                                attribute :>> isActor = false; 
                                attribute :>> isHuman = false; 
                                attribute :>> kind = PhysicalComponentKind::HARDWARE; 
                                attribute :>> nature = PhysicalComponentNature::NODE; 
                                port 'Motor Signal' : PhysicalPort { 
                                    @CapellaID { eid = "3ec2efee-41a0-4137-8a5b-4aa56489172e"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 2' : PhysicalPort { 
                                    @CapellaID { eid = "df46ef51-0971-4b08-acc8-89863a28808c"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 3' : PhysicalPort { 
                                    @CapellaID { eid = "590b1a74-6173-4cc4-9f85-9a9f30924d30"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 4' : PhysicalPort { 
                                    @CapellaID { eid = "b8912a84-9194-4584-ad0c-c7189b32cc43"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Gearbox' : PhysicalComponent { 
                                @CapellaID { eid = "964c95e2-5ec0-4697-97b0-db0b528bea10"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "4c63c271-5d4a-472b-aa06-fd251dbd49ff"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 2' : PhysicalPort { 
                                    @CapellaID { eid = "a209374b-abe0-462f-bb6f-a55bfe5c7467"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 3' : PhysicalPort { 
                                    @CapellaID { eid = "1fdff5cf-77a3-47eb-a13a-1c5472cfaba8"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Left Drive Shaft' : PhysicalComponent { 
                                @CapellaID { eid = "781318ca-52ee-4035-b386-53eb6bc1ed91"; } 
                                attribute :>> isAbstract = false; 
                                attribute :>> isActor = false; 
                                attribute :>> isHuman = false; 
                                attribute :>> kind = PhysicalComponentKind::UNSET; 
                                attribute :>> nature = PhysicalComponentNature::NODE; 
                                port 'PP 1' : PhysicalPort { 
                                    @CapellaID { eid = "de5bea9e-08dd-4c27-beb6-68c1bb095172"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 2' : PhysicalPort { 
                                    @CapellaID { eid = "8707ee05-a69c-41d7-a854-27512ea4c8e4"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Right Drive Shaft' : PhysicalComponent { 
                                @CapellaID { eid = "bd9efe14-150e-4cf9-978e-de75ed5b1fdd"; } 
                                attribute :>> isAbstract = false; 
                                attribute :>> isActor = false; 
                                attribute :>> isHuman = false; 
                                attribute :>> kind = PhysicalComponentKind::UNSET; 
                                attribute :>> nature = PhysicalComponentNature::NODE; 
                                port 'PP 1' : PhysicalPort { 
                                    @CapellaID { eid = "ba72b05a-5364-4e6e-b12c-ad49b0651ff0"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 2' : PhysicalPort { 
                                    @CapellaID { eid = "0a29e728-b967-4083-9b63-3a179eed3125"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Battery' : PhysicalComponent { 
                                doc /*
                                <p>A <strong>battery</strong> is an electrochemical cell that converts stored chemical energy into electrical energy. It is composed of one or more electrochemical cells, each of which contain two electrodes, an anode and a cathode, and an electrolyte that allows current to flow between them. Batteries are used in a wide range of applications, from powering flashlights and alarm clocks to providing energy for electric vehicles and large-scale energy storage systems. (<a href="https://en.wikipedia.org/wiki/Battery_(electricity)">Wikipedia</a>)</p>

                                */ 
                                @CapellaID { eid = "2c933777-d0c6-475d-be27-b1dd7f4a19ce"; } 
                                attribute :>> isAbstract = false; 
                                attribute :>> isActor = false; 
                                attribute :>> isHuman = false; 
                                attribute :>> kind = PhysicalComponentKind::HARDWARE; 
                                attribute :>> nature = PhysicalComponentNature::NODE; 
                                part 'BMS' : PhysicalComponent { 
                                    @CapellaID { eid = "8ffc7ac0-1a12-4f5a-a319-adf0d9281fb5"; } 
                                    attribute :>> isAbstract = false; 
                                    attribute :>> isActor = false; 
                                    attribute :>> isHuman = false; 
                                    attribute :>> kind = PhysicalComponentKind::UNSET; 
                                    attribute :>> nature = PhysicalComponentNature::NODE; 
                                    port 'PP 1' : PhysicalPort { 
                                        @CapellaID { eid = "0cb77d59-b0f7-4c83-b664-3176543f8943"; } 
                                        attribute :>> aggregationKind = AggregationKind::UNSET; 
                                        attribute :>> isFinal = false; 
                                        attribute :>> isAbstract = false; 
                                        attribute :>> isDerived = false; 
                                        attribute :>> isPartOfKey = false; 
                                        attribute :>> isReadOnly = false; 
                                        attribute :>> isStatic = false; 
                                        attribute :>> isMaxInclusive = false; 
                                        attribute :>> isMinInclusive = false; 
                                        attribute :>> isOrdered = false; 
                                        attribute :>> isUnique = false; 
                                    }  
                                }  
                                port 'Battery Temp Sensor' : PhysicalPort { 
                                    @CapellaID { eid = "107226ec-bb2c-4dd9-9537-93614d75873e"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'B+' : PhysicalPort { 
                                    @CapellaID { eid = "e9afed31-1003-4857-b464-1317b40fc631"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'B-' : PhysicalPort { 
                                    @CapellaID { eid = "c1fba631-1683-4e66-9ab1-41dc6e1eab64"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                ref :>> ownedPhysicalComponents =  ('eRod_Autonomous_Vehicle_2024 Project'::'eRod_Autonomous_Vehicle_2024'::'Physical Architecture'::'Structure'::'Physical System'.'eRod'.'Power Train'.'Battery'.'BMS'); 
                            }  
                            part 'Drive Control' : PhysicalComponent { 
                                @CapellaID { eid = "3d005328-163d-4cdb-a714-93b918629983"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "70a1a272-9004-474b-9a7f-dbb2197bdffd"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 2' : PhysicalPort { 
                                    @CapellaID { eid = "01c472a0-3594-44c0-9672-4c2013b8611d"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 3' : PhysicalPort { 
                                    @CapellaID { eid = "6c839716-38b6-48b9-8d82-d18e0fdb659c"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'B+' : PhysicalPort { 
                                    @CapellaID { eid = "6011d0e6-64b7-465b-933a-4c1354f8d175"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'B-' : PhysicalPort { 
                                    @CapellaID { eid = "cf5f86da-39ed-4bee-929f-a66c84df6963"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Electrical Box Rear' : PhysicalComponent { 
                                @CapellaID { eid = "b2d0521f-69ad-48f0-a830-45f2a825b5a9"; } 
                                attribute :>> isAbstract = false; 
                                attribute :>> isActor = false; 
                                attribute :>> isHuman = false; 
                                attribute :>> kind = PhysicalComponentKind::HARDWARE; 
                                attribute :>> nature = PhysicalComponentNature::NODE; 
                                port 'B+DC' : PhysicalPort { 
                                    @CapellaID { eid = "203dfbff-384f-4cb3-9897-4c711519c8f7"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'B- DC' : PhysicalPort { 
                                    @CapellaID { eid = "86117ebf-9503-45ef-94bd-d90444f090b2"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Number Plate' : PhysicalPort { 
                                    @CapellaID { eid = "b16ae4f3-7a6c-4fd1-b0c2-3ae69de50c53"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Fan' : PhysicalPort { 
                                    @CapellaID { eid = "f10ab739-1b47-4f3f-9a13-437b4817260d"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Right Rear Lights' : PhysicalPort { 
                                    @CapellaID { eid = "4ed20513-663f-4368-9088-a04b4ab0309b"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Battery Temperature Sensor' : PhysicalPort { 
                                    @CapellaID { eid = "2ce0a0cf-d0fc-467b-89fc-079bb58b8a86"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Motor encoder' : PhysicalPort { 
                                    @CapellaID { eid = "c2b2ce71-1ac9-4669-96b6-0a3ff44dd69d"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Seat Switch' : PhysicalPort { 
                                    @CapellaID { eid = "88d7ff0d-3218-4a05-91c0-77bf45934549"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Front Electrical Box' : PhysicalPort { 
                                    @CapellaID { eid = "51d3f0e3-3fcc-4760-8c28-8208280e842d"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Left Rear Lights' : PhysicalPort { 
                                    @CapellaID { eid = "ae5b75ec-5582-48ea-a384-ee38c81d8ed9"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Motor Signal' : PhysicalPort { 
                                    @CapellaID { eid = "5e595f9d-ac90-4048-9f86-6a93d9824e47"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'B+' : PhysicalPort { 
                                    @CapellaID { eid = "d15c2f15-6a0b-447c-812e-46b50d12de4d"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'B-' : PhysicalPort { 
                                    @CapellaID { eid = "c3c38bd0-41df-4931-b16e-a7558fe7f7cf"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'BMS' : PhysicalPort { 
                                    @CapellaID { eid = "b7af9158-34e5-4caf-9ff1-23befe410eb9"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Seat Sensor Left' : PhysicalPort { 
                                    @CapellaID { eid = "62797a0a-0839-4085-a580-5d29091faec8"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Seat Sensor Right' : PhysicalPort { 
                                    @CapellaID { eid = "327d2d06-9d84-4fba-b890-391598533429"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Display' : PhysicalPort { 
                                    @CapellaID { eid = "56882a44-4afa-462f-b6a6-235748a4d78f"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Rear Fog Light Left' : PhysicalPort { 
                                    @CapellaID { eid = "a75cb62e-ace5-4e0b-b287-ac006d8d4169"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Rear Fog Light Right' : PhysicalPort { 
                                    @CapellaID { eid = "c100d314-1b40-43f0-8878-46df48bf16c4"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Accelerator Pedal' : PhysicalPort { 
                                    @CapellaID { eid = "403a6f87-3133-4378-b197-da004f665304"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'Hand Brake' : PhysicalPort { 
                                    @CapellaID { eid = "3261cebf-e6b6-4e7b-b1d3-f0062fbf57f1"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            interface '9e1ac847-257d-4fdb-aae7-7f5934188c31' : PhysicalLink 
                                connect sourcePhysicalPort ::> 'eRod_Autonomous_Vehicle_2024 Project'::'eRod_Autonomous_Vehicle_2024'::'Physical Architecture'::'Structure'::'Physical System'.'eRod'.'Power Train'.'Electrical Motor'.'Motor Signal'
                                to targetPhysicalPort ::> 'eRod_Autonomous_Vehicle_2024 Project'::'eRod_Autonomous_Vehicle_2024'::'Physical Architecture'::'Structure'::'Physical System'.'eRod'.'Power Train'.'Gearbox'.'PP 1' {
                                @CapellaID { eid = "9e1ac847-257d-4fdb-aae7-7f5934188c31"; } 
                                attribute :>> interfaceName = "Torque"; 
                            }  
                            interface 'c181ac6a-8834-4fe0-bf3f-15f412dd556c' : PhysicalLink 
                                connect sourcePhysicalPort ::> 'eRod_Autonomous_Vehicle_2024 Project'::'eRod_Autonomous_Vehicle_2024'::'Physical Architecture'::'Structure'::'Physical System'.'eRod'.'Power Train'.'Right Drive Shaft'.'PP 1'
                                to targetPhysicalPort ::> 'eRod_Autonomous_Vehicle_2024 Project'::'eRod_Autonomous_Vehicle_2024'::'Physical Architecture'::'Structure'::'Physical System'.'eRod'.'Power Train'.'Gearbox'.'PP 2' {
                                @CapellaID { eid = "c181ac6a-8834-4fe0-bf3f-15f412dd556c"; } 
                                attribute :>> interfaceName = "Gearbox Right Shaft"; 
                            }  
                            interface 'd44cb4cb-b2e7-48e5-80d9-9221ace744b5' : PhysicalLink 
                                connect sourcePhysicalPort ::> 'eRod_Autonomous_Vehicle_2024 Project'::'eRod_Autonomous_Vehicle_2024'::'Physical Architecture'::'Structure'::'Physical System'.'eRod'.'Power Train'.'Gearbox'.'PP 3'
                                to targetPhysicalPort ::> 'eRod_Autonomous_Vehicle_2024 Project'::'eRod_Autonomous_Vehicle_2024'::'Physical Architecture'::'Structure'::'Physical System'.'eRod'.'Power Train'.'Left Drive Shaft'.'PP 1' {
                                @CapellaID { eid = "d44cb4cb-b2e7-48e5-80d9-9221ace744b5"; } 
                                attribute :>> interfaceName = "Gearbox Left Shaft"; 
                            }  
                            interface '7fb58c43-14e4-4790-b471-29b6951dbc36' : PhysicalLink 
                                connect sourcePhysicalPort ::> 'eRod_Autonomous_Vehicle_2024 Project'::'eRod_Autonomous_Vehicle_2024'::'Physical Architecture'::'Structure'::'Physical System'.'eRod'.'Power Train'.'Drive Control'.'PP 1'
                                to targetPhysicalPort ::> 'eRod_Autonomous_Vehicle_2024 Project'::'eRod_Autonomous_Vehicle_2024'::'Physical Architecture'::'Structure'::'Physical System'.'eRod'.'Power Train'.'Electrical Motor'.'PP 2' {
                                @CapellaID { eid = "7fb58c43-14e4-4790-b471-29b6951dbc36"; } 
                                attribute :>> interfaceName = "Engine Cable U"; 
                            }  
                            interface 'ef92b6e9-1367-4eb7-a2b1-7493b0127f91' : PhysicalLink 
                                connect sourcePhysicalPort ::> 'eRod_Autonomous_Vehicle_2024 Project'::'eRod_Autonomous_Vehicle_2024'::'Physical Architecture'::'Structure'::'Physical System'.'eRod'.'Power Train'.'Drive Control'.'PP 2'
                                to targetPhysicalPort ::> 'eRod_Autonomous_Vehicle_2024 Project'::'eRod_Autonomous_Vehicle_2024'::'Physical Architecture'::'Structure'::'Physical System'.'eRod'.'Power Train'.'Electrical Motor'.'PP 3' {
                                @CapellaID { eid = "ef92b6e9-1367-4eb7-a2b1-7493b0127f91"; } 
                                attribute :>> interfaceName = "Engine Cable V"; 
                            }  
                            interface '0909d6d6-ad66-493c-b1ba-7da85967c36b' : PhysicalLink 
                                connect sourcePhysicalPort ::> 'eRod_Autonomous_Vehicle_2024 Project'::'eRod_Autonomous_Vehicle_2024'::'Physical Architecture'::'Structure'::'Physical System'.'eRod'.'Power Train'.'Drive Control'.'PP 3'
                                to targetPhysicalPort ::> 'eRod_Autonomous_Vehicle_2024 Project'::'eRod_Autonomous_Vehicle_2024'::'Physical Architecture'::'Structure'::'Physical System'.'eRod'.'Power Train'.'Electrical Motor'.'PP 4' {
                                @CapellaID { eid = "0909d6d6-ad66-493c-b1ba-7da85967c36b"; } 
                                attribute :>> interfaceName = "Engine Cable W"; 
                            }  
                            interface 'd3735bbd-8422-415b-8b23-658dcbc3e67d' : PhysicalLink 
                                connect sourcePhysicalPort ::> 'eRod_Autonomous_Vehicle_2024 Project'::'eRod_Autonomous_Vehicle_2024'::'Physical Architecture'::'Structure'::'Physical System'.'eRod'.'Power Train'.'Electrical Box Rear'.'B+DC'
                                to targetPhysicalPort ::> 'eRod_Autonomous_Vehicle_2024 Project'::'eRod_Autonomous_Vehicle_2024'::'Physical Architecture'::'Structure'::'Physical System'.'eRod'.'Power Train'.'Drive Control'.'B+' {
                                @CapellaID { eid = "d3735bbd-8422-415b-8b23-658dcbc3e67d"; } 
                                attribute :>> interfaceName = "Battery Cable Plus"; 
                            }  
                            interface '0f2cd6e2-f2d2-4c67-ab99-1ab8b7866a13' : PhysicalLink 
                                connect sourcePhysicalPort ::> 'eRod_Autonomous_Vehicle_2024 Project'::'eRod_Autonomous_Vehicle_2024'::'Physical Architecture'::'Structure'::'Physical System'.'eRod'.'Power Train'.'Electrical Box Rear'.'B- DC'
                                to targetPhysicalPort ::> 'eRod_Autonomous_Vehicle_2024 Project'::'eRod_Autonomous_Vehicle_2024'::'Physical Architecture'::'Structure'::'Physical System'.'eRod'.'Power Train'.'Drive Control'.'B-' {
                                @CapellaID { eid = "0f2cd6e2-f2d2-4c67-ab99-1ab8b7866a13"; } 
                                attribute :>> interfaceName = "Battery Cable Minus"; 
                            }  
                            interface '80da1602-88b8-40c3-81b5-18d93bb006c8' : PhysicalLink 
                                connect sourcePhysicalPort ::> 'eRod_Autonomous_Vehicle_2024 Project'::'eRod_Autonomous_Vehicle_2024'::'Physical Architecture'::'Structure'::'Physical System'.'eRod'.'Power Train'.'Electrical Motor'.'Motor Signal'
                                to targetPhysicalPort ::> 'eRod_Autonomous_Vehicle_2024 Project'::'eRod_Autonomous_Vehicle_2024'::'Physical Architecture'::'Structure'::'Physical System'.'eRod'.'Power Train'.'Electrical Box Rear'.'Motor Signal' {
                                @CapellaID { eid = "80da1602-88b8-40c3-81b5-18d93bb006c8"; } 
                                attribute :>> interfaceName = "PL 9"; 
                            }  
                            interface '9c436bce-2305-4637-ae8e-974b73379030' : PhysicalLink 
                                connect sourcePhysicalPort ::> 'eRod_Autonomous_Vehicle_2024 Project'::'eRod_Autonomous_Vehicle_2024'::'Physical Architecture'::'Structure'::'Physical System'.'eRod'.'Power Train'.'Battery'.'Battery Temp Sensor'
                                to targetPhysicalPort ::> 'eRod_Autonomous_Vehicle_2024 Project'::'eRod_Autonomous_Vehicle_2024'::'Physical Architecture'::'Structure'::'Physical System'.'eRod'.'Power Train'.'Electrical Box Rear'.'Battery Temperature Sensor' {
                                @CapellaID { eid = "9c436bce-2305-4637-ae8e-974b73379030"; } 
                                attribute :>> interfaceName = "EL"; 
                            }  
                            interface '25d06eda-38a4-4b3e-87ad-cdd124b86de2' : PhysicalLink 
                                connect sourcePhysicalPort ::> 'eRod_Autonomous_Vehicle_2024 Project'::'eRod_Autonomous_Vehicle_2024'::'Physical Architecture'::'Structure'::'Physical System'.'eRod'.'Power Train'.'Battery'.'B+'
                                to targetPhysicalPort ::> 'eRod_Autonomous_Vehicle_2024 Project'::'eRod_Autonomous_Vehicle_2024'::'Physical Architecture'::'Structure'::'Physical System'.'eRod'.'Power Train'.'Electrical Box Rear'.'B+' {
                                @CapellaID { eid = "25d06eda-38a4-4b3e-87ad-cdd124b86de2"; } 
                                attribute :>> interfaceName = "EL"; 
                            }  
                            interface 'ca0d95e3-0bd2-49eb-9216-d42f229b7d19' : PhysicalLink 
                                connect sourcePhysicalPort ::> 'eRod_Autonomous_Vehicle_2024 Project'::'eRod_Autonomous_Vehicle_2024'::'Physical Architecture'::'Structure'::'Physical System'.'eRod'.'Power Train'.'Battery'.'B-'
                                to targetPhysicalPort ::> 'eRod_Autonomous_Vehicle_2024 Project'::'eRod_Autonomous_Vehicle_2024'::'Physical Architecture'::'Structure'::'Physical System'.'eRod'.'Power Train'.'Electrical Box Rear'.'B-' {
                                @CapellaID { eid = "ca0d95e3-0bd2-49eb-9216-d42f229b7d19"; } 
                                attribute :>> interfaceName = "EL"; 
                            }  
                            interface 'c27f3dec-8f1b-4b61-ba52-43bac7aa4bb6' : PhysicalLink 
                                connect sourcePhysicalPort ::> 'eRod_Autonomous_Vehicle_2024 Project'::'eRod_Autonomous_Vehicle_2024'::'Physical Architecture'::'Structure'::'Physical System'.'eRod'.'Power Train'.'Battery'.'BMS'.'PP 1'
                                to targetPhysicalPort ::> 'eRod_Autonomous_Vehicle_2024 Project'::'eRod_Autonomous_Vehicle_2024'::'Physical Architecture'::'Structure'::'Physical System'.'eRod'.'Power Train'.'Electrical Box Rear'.'BMS' {
                                @CapellaID { eid = "c27f3dec-8f1b-4b61-ba52-43bac7aa4bb6"; } 
                                attribute :>> interfaceName = "EL"; 
                            }  
                            ref :>> ownedPhysicalComponents =  ('eRod_Autonomous_Vehicle_2024 Project'::'eRod_Autonomous_Vehicle_2024'::'Physical Architecture'::'Structure'::'Physical System'.'eRod'.'Power Train'.'Electrical Motor',
                            'eRod_Autonomous_Vehicle_2024 Project'::'eRod_Autonomous_Vehicle_2024'::'Physical Architecture'::'Structure'::'Physical System'.'eRod'.'Power Train'.'Gearbox',
                            'eRod_Autonomous_Vehicle_2024 Project'::'eRod_Autonomous_Vehicle_2024'::'Physical Architecture'::'Structure'::'Physical System'.'eRod'.'Power Train'.'Left Drive Shaft',
                            'eRod_Autonomous_Vehicle_2024 Project'::'eRod_Autonomous_Vehicle_2024'::'Physical Architecture'::'Structure'::'Physical System'.'eRod'.'Power Train'.'Right Drive Shaft',
                            'eRod_Autonomous_Vehicle_2024 Project'::'eRod_Autonomous_Vehicle_2024'::'Physical Architecture'::'Structure'::'Physical System'.'eRod'.'Power Train'.'Battery',
                            'eRod_Autonomous_Vehicle_2024 Project'::'eRod_Autonomous_Vehicle_2024'::'Physical Architecture'::'Structure'::'Physical System'.'eRod'.'Power Train'.'Drive Control',
                            'eRod_Autonomous_Vehicle_2024 Project'::'eRod_Autonomous_Vehicle_2024'::'Physical Architecture'::'Structure'::'Physical System'.'eRod'.'Power Train'.'Electrical Box Rear'); 
                            ref :>> ownedPhysicalLinks =  ('eRod_Autonomous_Vehicle_2024 Project'::'eRod_Autonomous_Vehicle_2024'::'Physical Architecture'::'Structure'::'Physical System'.'eRod'.'Power Train'.'9e1ac847-257d-4fdb-aae7-7f5934188c31',
                            'eRod_Autonomous_Vehicle_2024 Project'::'eRod_Autonomous_Vehicle_2024'::'Physical Architecture'::'Structure'::'Physical System'.'eRod'.'Power Train'.'c181ac6a-8834-4fe0-bf3f-15f412dd556c',
                            'eRod_Autonomous_Vehicle_2024 Project'::'eRod_Autonomous_Vehicle_2024'::'Physical Architecture'::'Structure'::'Physical System'.'eRod'.'Power Train'.'d44cb4cb-b2e7-48e5-80d9-9221ace744b5',
                            'eRod_Autonomous_Vehicle_2024 Project'::'eRod_Autonomous_Vehicle_2024'::'Physical Architecture'::'Structure'::'Physical System'.'eRod'.'Power Train'.'7fb58c43-14e4-4790-b471-29b6951dbc36',
                            'eRod_Autonomous_Vehicle_2024 Project'::'eRod_Autonomous_Vehicle_2024'::'Physical Architecture'::'Structure'::'Physical System'.'eRod'.'Power Train'.'ef92b6e9-1367-4eb7-a2b1-7493b0127f91',
                            'eRod_Autonomous_Vehicle_2024 Project'::'eRod_Autonomous_Vehicle_2024'::'Physical Architecture'::'Structure'::'Physical System'.'eRod'.'Power Train'.'0909d6d6-ad66-493c-b1ba-7da85967c36b',
                            'eRod_Autonomous_Vehicle_2024 Project'::'eRod_Autonomous_Vehicle_2024'::'Physical Architecture'::'Structure'::'Physical System'.'eRod'.'Power Train'.'d3735bbd-8422-415b-8b23-658dcbc3e67d',
                            'eRod_Autonomous_Vehicle_2024 Project'::'eRod_Autonomous_Vehicle_2024'::'Physical Architecture'::'Structure'::'Physical System'.'eRod'.'Power Train'.'0f2cd6e2-f2d2-4c67-ab99-1ab8b7866a13',
                            'eRod_Autonomous_Vehicle_2024 Project'::'eRod_Autonomous_Vehicle_2024'::'Physical Architecture'::'Structure'::'Physical System'.'eRod'.'Power Train'.'80da1602-88b8-40c3-81b5-18d93bb006c8',
                            'eRod_Autonomous_Vehicle_2024 Project'::'eRod_Autonomous_Vehicle_2024'::'Physical Architecture'::'Structure'::'Physical System'.'eRod'.'Power Train'.'9c436bce-2305-4637-ae8e-974b73379030',
                            'eRod_Autonomous_Vehicle_2024 Project'::'eRod_Autonomous_Vehicle_2024'::'Physical Architecture'::'Structure'::'Physical System'.'eRod'.'Power Train'.'25d06eda-38a4-4b3e-87ad-cdd124b86de2',
                            'eRod_Autonomous_Vehicle_2024 Project'::'eRod_Autonomous_Vehicle_2024'::'Physical Architecture'::'Structure'::'Physical System'.'eRod'.'Power Train'.'ca0d95e3-0bd2-49eb-9216-d42f229b7d19',
                            'eRod_Autonomous_Vehicle_2024 Project'::'eRod_Autonomous_Vehicle_2024'::'Physical Architecture'::'Structure'::'Physical System'.'eRod'.'Power Train'.'c27f3dec-8f1b-4b61-ba52-43bac7aa4bb6'); 
                        }  
                        part 'Front Left Wheel' : PhysicalComponent { 
                            @CapellaID { eid = "af5a5655-8759-4518-9d6e-20d4cda416c2"; } 
                            attribute :>> isAbstract = false; 
                            attribute :>> isActor = false; 
                            attribute :>> isHuman = false; 
                            attribute :>> kind = PhysicalComponentKind::HARDWARE; 
                            attribute :>> nature = PhysicalComponentNature::NODE; 
                            part 'Right Front Tire' : PhysicalComponent { 
                                @CapellaID { eid = "39147860-b4d8-480a-8dca-c6017b1abeb4"; } 
                                attribute :>> isAbstract = false; 
                                attribute :>> isActor = false; 
                                attribute :>> isHuman = false; 
                                attribute :>> kind = PhysicalComponentKind::UNSET; 
                                attribute :>> nature = PhysicalComponentNature::NODE; 
                                port 'PP 1' : PhysicalPort { 
                                    @CapellaID { eid = "df98b137-13ac-4bf3-a4c9-f2cddc4b5645"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                    ref allocation '5aa6e2e7-ac95-4ef5-a126-eb04b6984f55' : ComponentPortAllocation
                                        allocate allocatedPort ::> 'eRod_Autonomous_Vehicle_2024 Project'::'eRod_Autonomous_Vehicle_2024'::'Physical Architecture'::'Structure'::'Physical System'.'eRod'.'Front Left Wheel'.'Right Front Tire'.'PP 1'
                                        to allocatingPort ::> 'eRod_Autonomous_Vehicle_2024 Project'::'eRod_Autonomous_Vehicle_2024'::'Physical Architecture'::'Structure'::'Physical System'.'Right Front Tiier'.'CP 1'; 
                                    ref :>> ownedComponentPortAllocations =  ('eRod_Autonomous_Vehicle_2024 Project'::'eRod_Autonomous_Vehicle_2024'::'Physical Architecture'::'Structure'::'Physical System'.'eRod'.'Front Left Wheel'.'Right Front Tire'.'PP 1'.'5aa6e2e7-ac95-4ef5-a126-eb04b6984f55'); 
                                }  
                                port 'PP 2' : PhysicalPort { 
                                    @CapellaID { eid = "25bf2278-4a0d-4a42-93cc-36c62003559c"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                    ref allocation '543a1196-7896-4eb8-8b68-ca7844f6cddd' : ComponentPortAllocation
                                        allocate allocatedPort ::> 'eRod_Autonomous_Vehicle_2024 Project'::'eRod_Autonomous_Vehicle_2024'::'Physical Architecture'::'Structure'::'Physical System'.'eRod'.'Front Left Wheel'.'Right Front Tire'.'PP 2'
                                        to allocatingPort ::> 'eRod_Autonomous_Vehicle_2024 Project'::'eRod_Autonomous_Vehicle_2024'::'Physical Architecture'::'Structure'::'Physical System'.'Right Front Tiier'.'CP 2'; 
                                    ref :>> ownedComponentPortAllocations =  ('eRod_Autonomous_Vehicle_2024 Project'::'eRod_Autonomous_Vehicle_2024'::'Physical Architecture'::'Structure'::'Physical System'.'eRod'.'Front Left Wheel'.'Right Front Tire'.'PP 2'.'543a1196-7896-4eb8-8b68-ca7844f6cddd'); 
                                }  
                                allocation '2a7a1180-eaf7-4bad-b36c-a415707fd5c1' : PartDeploymentLink
                                    allocate deployed ::> 'eRod_Autonomous_Vehicle_2024 Project'::'eRod_Autonomous_Vehicle_2024'::'Physical Architecture'::'Structure'::'Physical System'.'eRod'.'Front Left Wheel'.'Right Front Tire'
                                    to deploying ::> 'eRod_Autonomous_Vehicle_2024 Project'::'eRod_Autonomous_Vehicle_2024'::'Physical Architecture'::'Structure'::'Physical System'.'Right Front Tiier'; 
                            }  
                            port 'PP 2' : PhysicalPort { 
                                @CapellaID { eid = "c5fabbc2-91be-420b-b873-a8b759c6fd3b"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 3' : PhysicalPort { 
                                @CapellaID { eid = "e94c72fb-4338-4c33-82b5-74ac446bc180"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            interface 'caa37548-e9df-4c93-bc9a-6431dc2f9561' : PhysicalLink 
                                connect sourcePhysicalPort ::> 'eRod_Autonomous_Vehicle_2024 Project'::'eRod_Autonomous_Vehicle_2024'::'Physical Architecture'::'Structure'::'Physical System'.'eRod'.'Front Left Wheel'.'Right Front Tire'.'PP 1'
                                to targetPhysicalPort ::> 'eRod_Autonomous_Vehicle_2024 Project'::'eRod_Autonomous_Vehicle_2024'::'Physical Architecture'::'Structure'::'Physical System'.'eRod'.'Front Left Wheel'.'PP 2' {
                                @CapellaID { eid = "caa37548-e9df-4c93-bc9a-6431dc2f9561"; } 
                                attribute :>> interfaceName = "PL 1"; 
                            }  
                            ref :>> ownedPhysicalComponents =  ('eRod_Autonomous_Vehicle_2024 Project'::'eRod_Autonomous_Vehicle_2024'::'Physical Architecture'::'Structure'::'Physical System'.'eRod'.'Front Left Wheel'.'Right Front Tire'); 
                            ref :>> ownedPhysicalLinks =  ('eRod_Autonomous_Vehicle_2024 Project'::'eRod_Autonomous_Vehicle_2024'::'Physical Architecture'::'Structure'::'Physical System'.'eRod'.'Front Left Wheel'.'caa37548-e9df-4c93-bc9a-6431dc2f9561'); 
                        }  
                        part 'Front Right Wheel' : PhysicalComponent { 
                            @CapellaID { eid = "6230cf7c-77e3-4a94-9d5b-9374f846ea12"; } 
                            attribute :>> isAbstract = false; 
                            attribute :>> isActor = false; 
                            attribute :>> isHuman = false; 
                            attribute :>> kind = PhysicalComponentKind::HARDWARE; 
                            attribute :>> nature = PhysicalComponentNature::NODE; 
                            part 'Left Front Tire' : PhysicalComponent { 
                                @CapellaID { eid = "b58f1205-48ac-449f-b08f-95ca5bf5a467"; } 
                                attribute :>> isAbstract = false; 
                                attribute :>> isActor = false; 
                                attribute :>> isHuman = false; 
                                attribute :>> kind = PhysicalComponentKind::UNSET; 
                                attribute :>> nature = PhysicalComponentNature::NODE; 
                                port 'PP 1' : PhysicalPort { 
                                    @CapellaID { eid = "dc25d194-627a-4627-917d-c4146dbadb20"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 2' : PhysicalPort { 
                                    @CapellaID { eid = "74276398-cb83-49b0-b69f-8a27c3925100"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                    ref allocation '7ef261b1-0661-4485-8c8c-c83f223c7e0a' : ComponentPortAllocation
                                        allocate allocatedPort ::> 'eRod_Autonomous_Vehicle_2024 Project'::'eRod_Autonomous_Vehicle_2024'::'Physical Architecture'::'Structure'::'Physical System'.'eRod'.'Front Right Wheel'.'Left Front Tire'.'PP 2'
                                        to allocatingPort ::> 'eRod_Autonomous_Vehicle_2024 Project'::'eRod_Autonomous_Vehicle_2024'::'Physical Architecture'::'Structure'::'Physical System'.'Left Front Tire'.'CP 3'; 
                                    ref :>> ownedComponentPortAllocations =  ('eRod_Autonomous_Vehicle_2024 Project'::'eRod_Autonomous_Vehicle_2024'::'Physical Architecture'::'Structure'::'Physical System'.'eRod'.'Front Right Wheel'.'Left Front Tire'.'PP 2'.'7ef261b1-0661-4485-8c8c-c83f223c7e0a'); 
                                }  
                                allocation '8fb4f7ae-6ced-4028-8b88-8692d49742e4' : PartDeploymentLink
                                    allocate deployed ::> 'eRod_Autonomous_Vehicle_2024 Project'::'eRod_Autonomous_Vehicle_2024'::'Physical Architecture'::'Structure'::'Physical System'.'eRod'.'Front Right Wheel'.'Left Front Tire'
                                    to deploying ::> 'eRod_Autonomous_Vehicle_2024 Project'::'eRod_Autonomous_Vehicle_2024'::'Physical Architecture'::'Structure'::'Physical System'.'Left Front Tire'; 
                            }  
                            port 'PP 2' : PhysicalPort { 
                                @CapellaID { eid = "d74e7e02-7657-41cb-8255-0bfdd05dfe46"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '14eea4e2-263f-4203-92f6-f4e1455ee5e2' : ComponentPortAllocation
                                    allocate allocatedPort ::> 'eRod_Autonomous_Vehicle_2024 Project'::'eRod_Autonomous_Vehicle_2024'::'Physical Architecture'::'Structure'::'Physical System'.'eRod'.'Front Right Wheel'.'PP 2'
                                    to allocatingPort ::> 'eRod_Autonomous_Vehicle_2024 Project'::'eRod_Autonomous_Vehicle_2024'::'Physical Architecture'::'Structure'::'Physical System'.'Left Front Tire'.'CP 2'; 
                                ref :>> ownedComponentPortAllocations =  ('eRod_Autonomous_Vehicle_2024 Project'::'eRod_Autonomous_Vehicle_2024'::'Physical Architecture'::'Structure'::'Physical System'.'eRod'.'Front Right Wheel'.'PP 2'.'14eea4e2-263f-4203-92f6-f4e1455ee5e2'); 
                            }  
                            interface '96c0774a-2272-4932-a977-0a221c5c5a31' : PhysicalLink 
                                connect sourcePhysicalPort ::> 'eRod_Autonomous_Vehicle_2024 Project'::'eRod_Autonomous_Vehicle_2024'::'Physical Architecture'::'Structure'::'Physical System'.'eRod'.'Front Right Wheel'.'Left Front Tire'.'PP 1'
                                to targetPhysicalPort ::> 'eRod_Autonomous_Vehicle_2024 Project'::'eRod_Autonomous_Vehicle_2024'::'Physical Architecture'::'Structure'::'Physical System'.'eRod'.'Front Right Wheel'.'PP 2' {
                                @CapellaID { eid = "96c0774a-2272-4932-a977-0a221c5c5a31"; } 
                                attribute :>> interfaceName = "PL 1"; 
                            }  
                            ref :>> ownedPhysicalComponents =  ('eRod_Autonomous_Vehicle_2024 Project'::'eRod_Autonomous_Vehicle_2024'::'Physical Architecture'::'Structure'::'Physical System'.'eRod'.'Front Right Wheel'.'Left Front Tire'); 
                            ref :>> ownedPhysicalLinks =  ('eRod_Autonomous_Vehicle_2024 Project'::'eRod_Autonomous_Vehicle_2024'::'Physical Architecture'::'Structure'::'Physical System'.'eRod'.'Front Right Wheel'.'96c0774a-2272-4932-a977-0a221c5c5a31'); 
                        }  
                        part 'Rear Left Wheel' : PhysicalComponent { 
                            @CapellaID { eid = "0054001c-50f4-4e78-91c6-57cd53a34552"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "78886d1d-36f5-400f-a5d5-b847d92942a5"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Rear Right Wheel' : PhysicalComponent { 
                            @CapellaID { eid = "d1359bd9-1d7b-4e65-955f-d438c892cb48"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "2a3e655d-91c9-446a-98f1-3cbbd093b747"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Left Wheel Carrier' : PhysicalComponent { 
                            @CapellaID { eid = "5eb9a18e-3459-492c-a386-3a3827629551"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "f617f444-b474-4e65-8fe4-0f3e7aad846a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 2' : PhysicalPort { 
                                @CapellaID { eid = "4c91b327-95d1-4b9b-8f5c-a9f58448b420"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Right Wheel Carrier' : PhysicalComponent { 
                            @CapellaID { eid = "013ee8ac-f23c-45f0-9a05-53fe5d28bd41"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "bacb2683-058d-4ad8-b28f-6502555b5ac0"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 2' : PhysicalPort { 
                                @CapellaID { eid = "2ecc1b81-470e-4a80-8826-8af5a0f331f8"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Electrical Box Front' : PhysicalComponent { 
                            @CapellaID { eid = "3fb37ed9-a002-4486-84bf-ff076a1d008c"; } 
                            attribute :>> isAbstract = false; 
                            attribute :>> isActor = false; 
                            attribute :>> isHuman = false; 
                            attribute :>> kind = PhysicalComponentKind::HARDWARE; 
                            attribute :>> nature = PhysicalComponentNature::NODE; 
                            port 'Indicator L' : PhysicalPort { 
                                @CapellaID { eid = "81dca144-6977-499c-81a9-fd815a991da4"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'Rear Electrical Box' : PhysicalPort { 
                                @CapellaID { eid = "d80a4434-b9f9-4038-a8ca-edb98a3ea504"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'High Beam L' : PhysicalPort { 
                                @CapellaID { eid = "8fb18c96-03c4-4bc1-ba4a-17e6bde510a3"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'Lights Right' : PhysicalPort { 
                                @CapellaID { eid = "c313c147-f9d1-4848-8378-96c1edabfbfa"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'Lights Left' : PhysicalPort { 
                                @CapellaID { eid = "fa8ed4d5-70f8-415a-af80-4bb1d11674f8"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'Brake Pedal' : PhysicalPort { 
                                @CapellaID { eid = "1a55b843-ce2c-4a09-8427-0c7744a119ba"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'Brake Fluid' : PhysicalPort { 
                                @CapellaID { eid = "cdbded64-14d6-4b1f-b322-48ca189c03ed"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'Hazard Light Switch' : PhysicalPort { 
                                @CapellaID { eid = "7096862f-99bc-4d61-aed7-48be47fb2794"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'Emergency Switch' : PhysicalPort { 
                                @CapellaID { eid = "26988201-9230-4528-9070-59d44d63b3ae"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'Ignition Lock' : PhysicalPort { 
                                @CapellaID { eid = "0d8aa18a-2325-4bf0-ac89-eba3e03dbbcb"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'Light Switch' : PhysicalPort { 
                                @CapellaID { eid = "4697de38-d9ff-4bf9-86bc-125abec7e01b"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'Direction Switch' : PhysicalPort { 
                                @CapellaID { eid = "7459dbb0-5658-4a7c-b0f9-1a9ad8f2c69b"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'Indicator' : PhysicalPort { 
                                @CapellaID { eid = "fafce95d-a243-410f-99ff-724da4a947bf"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'Horn' : PhysicalPort { 
                                @CapellaID { eid = "b325d4f0-94a4-4715-81e2-e3abac78b435"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Horn' : PhysicalComponent { 
                            @CapellaID { eid = "9073c216-0a7b-43ab-ab84-c2e7584f3f63"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "658eff53-9e5c-4bf8-ab16-5a80f4b2f780"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Dashboard' : PhysicalComponent { 
                            @CapellaID { eid = "071dcd9f-dc8f-4a79-aa50-7fb7dfa52763"; } 
                            attribute :>> isAbstract = false; 
                            attribute :>> isActor = false; 
                            attribute :>> isHuman = false; 
                            attribute :>> kind = PhysicalComponentKind::HARDWARE; 
                            attribute :>> nature = PhysicalComponentNature::NODE; 
                            part 'Hazard Light Switch' : PhysicalComponent { 
                                @CapellaID { eid = "388372b5-0b05-46a5-b711-102932d0370c"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "28137512-9fb9-4981-8c3a-1212ce425ccf"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Emergency Off Switch' : PhysicalComponent { 
                                @CapellaID { eid = "1b0848df-ad9c-46b6-a7b0-b89eda872f94"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "7fecff23-463e-4a78-81b4-3bfa3c3af576"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Ignition Lock' : PhysicalComponent { 
                                @CapellaID { eid = "d043a5ec-1f56-4e0b-b74e-a55244ee842b"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "20d1cc02-d814-410d-899b-b9ee0336f9fa"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'High Beam Switch' : PhysicalComponent { 
                                @CapellaID { eid = "0dd77ff6-1f5a-4576-8ad1-f9a4082b700b"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "512aba81-cebe-4cf6-86f9-8a1b0a902dd2"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Driving Direction Switch' : PhysicalComponent { 
                                @CapellaID { eid = "9db7f6b9-5820-4529-a3a2-b981ccd6eac2"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "aed5ba70-15c1-4957-bf19-8f5a5657d291"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Indicator Switch' : PhysicalComponent { 
                                @CapellaID { eid = "ef1dfddc-d701-4b55-b3bf-1b3530afa788"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "cf39085b-0979-4575-b3bf-8b03fe787234"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            ref :>> ownedPhysicalComponents =  ('eRod_Autonomous_Vehicle_2024 Project'::'eRod_Autonomous_Vehicle_2024'::'Physical Architecture'::'Structure'::'Physical System'.'eRod'.'Dashboard'.'Hazard Light Switch',
                            'eRod_Autonomous_Vehicle_2024 Project'::'eRod_Autonomous_Vehicle_2024'::'Physical Architecture'::'Structure'::'Physical System'.'eRod'.'Dashboard'.'Emergency Off Switch',
                            'eRod_Autonomous_Vehicle_2024 Project'::'eRod_Autonomous_Vehicle_2024'::'Physical Architecture'::'Structure'::'Physical System'.'eRod'.'Dashboard'.'Ignition Lock',
                            'eRod_Autonomous_Vehicle_2024 Project'::'eRod_Autonomous_Vehicle_2024'::'Physical Architecture'::'Structure'::'Physical System'.'eRod'.'Dashboard'.'High Beam Switch',
                            'eRod_Autonomous_Vehicle_2024 Project'::'eRod_Autonomous_Vehicle_2024'::'Physical Architecture'::'Structure'::'Physical System'.'eRod'.'Dashboard'.'Driving Direction Switch',
                            'eRod_Autonomous_Vehicle_2024 Project'::'eRod_Autonomous_Vehicle_2024'::'Physical Architecture'::'Structure'::'Physical System'.'eRod'.'Dashboard'.'Indicator Switch'); 
                        }  
                        part 'Fan' : PhysicalComponent { 
                            @CapellaID { eid = "3022555c-2b6c-485c-baa5-4c1bd6b89bdb"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "41069318-7a35-4636-a380-f04a4fc988e0"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Left High-Beam Light' : PhysicalComponent { 
                            @CapellaID { eid = "d2cd0d0e-555b-4a65-b5ca-72198aa24434"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "ebbe6020-6dcc-4102-867b-3579b05a7994"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Right High-Beam Light' : PhysicalComponent { 
                            @CapellaID { eid = "caa4146e-2dcd-46de-9714-b83fd6bd6fb2"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "6cc4e3bd-a570-43bf-ac56-dca92ca55818"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Left Low-Beam Light' : PhysicalComponent { 
                            @CapellaID { eid = "33b4e333-5a47-4087-afbd-56f1adc13970"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "8008a3b8-e583-40f5-9cfb-6e7b2e0ecd73"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Right Low-Beam Light' : PhysicalComponent { 
                            @CapellaID { eid = "93ddd19d-ae3e-4eb8-b749-f195beeea53d"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "b8c62717-afef-4090-b3dd-f95d7c627fa0"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Left Indicator Light' : PhysicalComponent { 
                            @CapellaID { eid = "33474944-7fea-4c37-8d29-cab3c7fe79a1"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "6fab6048-a49d-449f-a4f5-c34879f792ef"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Right Indicator Light' : PhysicalComponent { 
                            @CapellaID { eid = "86c571ac-5f91-4fe9-bc55-c0b8548bb722"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "973fbd60-4877-4c21-b605-72e10035414b"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Left Rear Light w Indicator' : PhysicalComponent { 
                            @CapellaID { eid = "6de17317-f089-49f4-bee7-52a55f62d414"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "817fc0da-ee25-40a9-bc62-1d82e73bde7a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Left Rear Light' : PhysicalComponent { 
                            @CapellaID { eid = "77872cb5-ba88-40f1-a964-3628fdf445f1"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "b634d8a3-6f4e-47bd-900b-3d1d13899fe1"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Right Rear Light' : PhysicalComponent { 
                            @CapellaID { eid = "3a33ca9c-f903-424e-a4e0-b0d268713dd4"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "e2928f5e-9161-484f-ae0d-f6f2f124b2d5"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Right Rear Light w Indicator' : PhysicalComponent { 
                            @CapellaID { eid = "3bb0a91b-1929-443e-bf71-de52053c2c50"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "0ec521d8-9765-4e86-a801-c9db6048d127"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Number Plate Lights' : PhysicalComponent { 
                            @CapellaID { eid = "3d008301-ee12-45b3-9965-e94fc7a9b7e5"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "e8043c79-6dac-4629-a902-736eb1821d8d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Left Side LIght' : PhysicalComponent { 
                            @CapellaID { eid = "fa143664-5880-41a3-bea2-9f0975dbd4dc"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "456ed37c-f274-4dd9-b433-aa8b102bc484"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Right Side Light' : PhysicalComponent { 
                            @CapellaID { eid = "e1f1372a-d886-466c-a244-2484d299f63d"; } 
                            attribute :>> isAbstract = false; 
                            attribute :>> isActor = false; 
                            attribute :>> isHuman = false; 
                            attribute :>> kind = PhysicalComponentKind::HARDWARE; 
                            attribute :>> nature = PhysicalComponentNature::NODE; 
                            port 'PP 2' : PhysicalPort { 
                                @CapellaID { eid = "64837d3e-d067-460e-bda9-3b1efc2aa886"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Charger' : PhysicalComponent { 
                            @CapellaID { eid = "70245927-a98c-4321-a02f-81cbd442edac"; } 
                            attribute :>> isAbstract = false; 
                            attribute :>> isActor = false; 
                            attribute :>> isHuman = false; 
                            attribute :>> kind = PhysicalComponentKind::HARDWARE; 
                            attribute :>> nature = PhysicalComponentNature::NODE; 
                        }  
                        part 'Gas Pedal' : PhysicalComponent { 
                            @CapellaID { eid = "4caf64f0-5541-423d-98ab-08a40d36c69d"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "0645750d-33cf-432c-970c-b6dbd5b83f56"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Brake Pedal' : PhysicalComponent { 
                            @CapellaID { eid = "2e85a37a-cdc0-4b39-a09c-5dd41be9127e"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "e7642e21-17a6-41d6-87d9-759926bb267b"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 2' : PhysicalPort { 
                                @CapellaID { eid = "91494d4b-17bf-488d-8ae4-217186b3cb72"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 3' : PhysicalPort { 
                                @CapellaID { eid = "c9e19a09-daf4-4a2e-8ac7-77eb2e409831"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Display' : PhysicalComponent { 
                            @CapellaID { eid = "2cbe55f4-501d-40df-b982-9d3dd5725854"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "f27f96ca-e8e8-469b-b923-5b371aee53ae"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Brakes' : PhysicalComponent { 
                            @CapellaID { eid = "3aa8247e-db31-4f04-bfba-4a79249f41f6"; } 
                            attribute :>> isAbstract = false; 
                            attribute :>> isActor = false; 
                            attribute :>> isHuman = false; 
                            attribute :>> kind = PhysicalComponentKind::UNSET; 
                            attribute :>> nature = PhysicalComponentNature::NODE; 
                            part 'Left Rear Brake Disk' : PhysicalComponent { 
                                @CapellaID { eid = "598de722-af8b-4199-a5f3-298a3f4087c3"; } 
                                attribute :>> isAbstract = false; 
                                attribute :>> isActor = false; 
                                attribute :>> isHuman = false; 
                                attribute :>> kind = PhysicalComponentKind::HARDWARE; 
                                attribute :>> nature = PhysicalComponentNature::NODE; 
                            }  
                            part 'Right Rear Brake Disk' : PhysicalComponent { 
                                @CapellaID { eid = "5cb3ade1-92fd-4cd8-910f-d9c9f4d07140"; } 
                                attribute :>> isAbstract = false; 
                                attribute :>> isActor = false; 
                                attribute :>> isHuman = false; 
                                attribute :>> kind = PhysicalComponentKind::HARDWARE; 
                                attribute :>> nature = PhysicalComponentNature::NODE; 
                            }  
                            part 'Left Front Brake Disk' : PhysicalComponent { 
                                @CapellaID { eid = "5db9a9aa-9725-4f31-802d-d01861a2c092"; } 
                                attribute :>> isAbstract = false; 
                                attribute :>> isActor = false; 
                                attribute :>> isHuman = false; 
                                attribute :>> kind = PhysicalComponentKind::HARDWARE; 
                                attribute :>> nature = PhysicalComponentNature::NODE; 
                            }  
                            part 'Right Front Brake Disk' : PhysicalComponent { 
                                @CapellaID { eid = "bf5b6dc1-5928-4b38-bc6d-107f46b4dad9"; } 
                                attribute :>> isAbstract = false; 
                                attribute :>> isActor = false; 
                                attribute :>> isHuman = false; 
                                attribute :>> kind = PhysicalComponentKind::HARDWARE; 
                                attribute :>> nature = PhysicalComponentNature::NODE; 
                            }  
                            part 'Brake Caliper Rear Left' : PhysicalComponent { 
                                @CapellaID { eid = "2c2c9907-5b94-43da-85ce-d7f50ddbd2a6"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "f3fd3a9b-37b1-4a07-9979-7e8d2b70f740"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 2' : PhysicalPort { 
                                    @CapellaID { eid = "e34ff905-fe85-4793-8902-5a477629316a"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Brake Caliper Rear Right' : PhysicalComponent { 
                                @CapellaID { eid = "7be6c52a-af00-4e76-ade3-24c70b1f655f"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "a21e9b62-ed71-4679-b673-26b4927298e0"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 2' : PhysicalPort { 
                                    @CapellaID { eid = "b3e4778e-8af3-403e-a694-70c428587de0"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Brake Caliper Front Left' : PhysicalComponent { 
                                @CapellaID { eid = "839c38b0-b9ea-43a0-8680-867ad9bbc7a3"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "caafc9fe-af96-4d63-802c-7aeb26805b05"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 2' : PhysicalPort { 
                                    @CapellaID { eid = "dcdf960d-f5e1-499d-9200-7cb2eda3305c"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Brake Caliper Front Right' : PhysicalComponent { 
                                @CapellaID { eid = "d0e563f6-fa2d-4b95-b37b-3fe069651c82"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "c8f454d8-6fcd-482a-a284-20e4e0ba81b0"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 2' : PhysicalPort { 
                                    @CapellaID { eid = "1e9ff8b8-24f0-40eb-b17e-5b139a3f8d3c"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Brake Boosster' : PhysicalComponent { 
                                @CapellaID { eid = "3a8ef5c5-a044-482c-8dda-a6d20fffcb95"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "8a911c33-5e35-4a0b-8c14-7cb13fd0db41"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 2' : PhysicalPort { 
                                    @CapellaID { eid = "28fbeb28-02fb-4e8d-a3be-d4108031dca8"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 3' : PhysicalPort { 
                                    @CapellaID { eid = "dd3444aa-7776-4c51-8d07-6f5b3952b5f9"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 4' : PhysicalPort { 
                                    @CapellaID { eid = "7582e4a0-5a14-4b99-bd00-7df325d28eaa"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 5' : PhysicalPort { 
                                    @CapellaID { eid = "925fce56-3973-4124-85dc-a4eb44d1ea81"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 6' : PhysicalPort { 
                                    @CapellaID { eid = "6570e239-66d4-4653-b772-8b78eacb1216"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            part 'Brake Fluid Container' : PhysicalComponent { 
                                @CapellaID { eid = "e9f160d0-ef68-4aca-a1af-8ac39c2b0842"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "3c9af554-c561-457e-b68a-83696ff92dc8"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 2' : PhysicalPort { 
                                    @CapellaID { eid = "dc9764f6-f326-47c0-a4c7-ce4ce8ecc537"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 3' : PhysicalPort { 
                                    @CapellaID { eid = "a0e9d35f-0737-4eb3-8eea-62bb95e9ad87"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 4' : PhysicalPort { 
                                    @CapellaID { eid = "64cfdf29-b728-45e2-b25b-e3270690efad"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                port 'PP 5' : PhysicalPort { 
                                    @CapellaID { eid = "f785f265-b832-421f-a0e7-bab6a45dc926"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            ref :>> ownedPhysicalComponents =  ('eRod_Autonomous_Vehicle_2024 Project'::'eRod_Autonomous_Vehicle_2024'::'Physical Architecture'::'Structure'::'Physical System'.'eRod'.'Brakes'.'Left Rear Brake Disk',
                            'eRod_Autonomous_Vehicle_2024 Project'::'eRod_Autonomous_Vehicle_2024'::'Physical Architecture'::'Structure'::'Physical System'.'eRod'.'Brakes'.'Right Rear Brake Disk',
                            'eRod_Autonomous_Vehicle_2024 Project'::'eRod_Autonomous_Vehicle_2024'::'Physical Architecture'::'Structure'::'Physical System'.'eRod'.'Brakes'.'Left Front Brake Disk',
                            'eRod_Autonomous_Vehicle_2024 Project'::'eRod_Autonomous_Vehicle_2024'::'Physical Architecture'::'Structure'::'Physical System'.'eRod'.'Brakes'.'Right Front Brake Disk',
                            'eRod_Autonomous_Vehicle_2024 Project'::'eRod_Autonomous_Vehicle_2024'::'Physical Architecture'::'Structure'::'Physical System'.'eRod'.'Brakes'.'Brake Caliper Rear Left',
                            'eRod_Autonomous_Vehicle_2024 Project'::'eRod_Autonomous_Vehicle_2024'::'Physical Architecture'::'Structure'::'Physical System'.'eRod'.'Brakes'.'Brake Caliper Rear Right',
                            'eRod_Autonomous_Vehicle_2024 Project'::'eRod_Autonomous_Vehicle_2024'::'Physical Architecture'::'Structure'::'Physical System'.'eRod'.'Brakes'.'Brake Caliper Front Left',
                            'eRod_Autonomous_Vehicle_2024 Project'::'eRod_Autonomous_Vehicle_2024'::'Physical Architecture'::'Structure'::'Physical System'.'eRod'.'Brakes'.'Brake Caliper Front Right',
                            'eRod_Autonomous_Vehicle_2024 Project'::'eRod_Autonomous_Vehicle_2024'::'Physical Architecture'::'Structure'::'Physical System'.'eRod'.'Brakes'.'Brake Boosster',
                            'eRod_Autonomous_Vehicle_2024 Project'::'eRod_Autonomous_Vehicle_2024'::'Physical Architecture'::'Structure'::'Physical System'.'eRod'.'Brakes'.'Brake Fluid Container'); 
                        }  
                        part 'Autonomous Vehicle System' : PhysicalComponent { 
                            @CapellaID { eid = "b06f1caa-2bb7-43e5-b08a-0850dc40118a"; } 
                            attribute :>> isAbstract = false; 
                            attribute :>> isActor = false; 
                            attribute :>> isHuman = false; 
                            attribute :>> kind = PhysicalComponentKind::UNSET; 
                            attribute :>> nature = PhysicalComponentNature::NODE; 
                            part 'Rear Camera' : PhysicalComponent { 
                                @CapellaID { eid = "2829fa88-07a3-46c4-a483-0aa31994520b"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "e02c9e5f-7b78-40c0-843e-8fd802cbf904"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                allocation '86a99bb9-486c-43db-ad37-3eb959a15b96' : PartDeploymentLink
                                    allocate deployed ::> 'eRod_Autonomous_Vehicle_2024 Project'::'eRod_Autonomous_Vehicle_2024'::'Physical Architecture'::'Structure'::'Physical System'.'eRod'.'Autonomous Vehicle System'.'Rear Camera'
                                    to deploying ::> 'eRod_Autonomous_Vehicle_2024 Project'::'eRod_Autonomous_Vehicle_2024'::'Physical Architecture'::'Structure'::'Physical System'.'Image Processing (Rear Camera)'; 
                            }  
                            part 'Side Camera (Left)' : PhysicalComponent { 
                                @CapellaID { eid = "fa8522ee-37e6-484a-bada-5c265a7460f1"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "b17203f2-f9a7-40a9-afde-ac2f20ab4aa7"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                allocation '638f4e31-8bc7-47f5-a54e-a7d8e211904e' : PartDeploymentLink
                                    allocate deployed ::> 'eRod_Autonomous_Vehicle_2024 Project'::'eRod_Autonomous_Vehicle_2024'::'Physical Architecture'::'Structure'::'Physical System'.'eRod'.'Autonomous Vehicle System'.'Side Camera (Left)'
                                    to deploying ::> 'eRod_Autonomous_Vehicle_2024 Project'::'eRod_Autonomous_Vehicle_2024'::'Physical Architecture'::'Structure'::'Physical System'.'Image Processing (Left Camera)'; 
                            }  
                            part 'Front Camera' : PhysicalComponent { 
                                @CapellaID { eid = "f46dd3c0-7006-49c8-8458-a55a8f6cef2f"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "95f3dbcd-08b5-495c-9daa-b82ec1f3d141"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                allocation '4fe07f85-a44c-45f6-a1a6-42ebc61f8554' : PartDeploymentLink
                                    allocate deployed ::> 'eRod_Autonomous_Vehicle_2024 Project'::'eRod_Autonomous_Vehicle_2024'::'Physical Architecture'::'Structure'::'Physical System'.'eRod'.'Autonomous Vehicle System'.'Front Camera'
                                    to deploying ::> 'eRod_Autonomous_Vehicle_2024 Project'::'eRod_Autonomous_Vehicle_2024'::'Physical Architecture'::'Structure'::'Physical System'.'Image Processing (Front Camera)'; 
                                allocation '9e3d53be-377f-45e2-8523-7885fdadd411' : PartDeploymentLink
                                    allocate deployed ::> 'eRod_Autonomous_Vehicle_2024 Project'::'eRod_Autonomous_Vehicle_2024'::'Physical Architecture'::'Structure'::'Physical System'.'eRod'.'Autonomous Vehicle System'.'Front Camera'
                                    to deploying ::> 'eRod_Autonomous_Vehicle_2024 Project'::'eRod_Autonomous_Vehicle_2024'::'Physical Architecture'::'Structure'::'Physical System'.'Sensors'.'Camera'; 
                            }  
                            part 'Side Camera (Right)' : PhysicalComponent { 
                                @CapellaID { eid = "f5eecd34-919e-4561-ab72-814bcee9a9a6"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "b6b44b88-b752-4e4c-a792-a2eaa6c1fe8d"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                allocation '6fc8f7f9-e7f0-4ac6-a1ce-fb761c5d36c5' : PartDeploymentLink
                                    allocate deployed ::> 'eRod_Autonomous_Vehicle_2024 Project'::'eRod_Autonomous_Vehicle_2024'::'Physical Architecture'::'Structure'::'Physical System'.'eRod'.'Autonomous Vehicle System'.'Side Camera (Right)'
                                    to deploying ::> 'eRod_Autonomous_Vehicle_2024 Project'::'eRod_Autonomous_Vehicle_2024'::'Physical Architecture'::'Structure'::'Physical System'.'Image Processing (Right Camera)'; 
                            }  
                            part 'LIDAR' : PhysicalComponent { 
                                @CapellaID { eid = "1bc44178-483b-4aa7-b56c-15d48290fdb0"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "49ca8874-a1d9-4e9f-a7c7-89df4a2d0c2c"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                            }  
                            interface '0a17f7b4-0b57-43b8-b516-449a2e74974f' : PhysicalLink 
                                connect sourcePhysicalPort ::> 'eRod_Autonomous_Vehicle_2024 Project'::'eRod_Autonomous_Vehicle_2024'::'Physical Architecture'::'Structure'::'Physical System'.'eRod'.'Autonomous Vehicle System'.'Side Camera (Right)'.'PP 1'
                                to targetPhysicalPort ::> 'eRod_Autonomous_Vehicle_2024 Project'::'eRod_Autonomous_Vehicle_2024'::'Physical Architecture'::'Structure'::'Physical System'.'eRod'.'AV Controller'.'PP 1' {
                                @CapellaID { eid = "0a17f7b4-0b57-43b8-b516-449a2e74974f"; } 
                                attribute :>> interfaceName = "Network 3"; 
                            }  
                            interface 'fd876190-16a4-43d6-a680-4e25f9972ed8' : PhysicalLink 
                                connect sourcePhysicalPort ::> 'eRod_Autonomous_Vehicle_2024 Project'::'eRod_Autonomous_Vehicle_2024'::'Physical Architecture'::'Structure'::'Physical System'.'eRod'.'Autonomous Vehicle System'.'Side Camera (Left)'.'PP 1'
                                to targetPhysicalPort ::> 'eRod_Autonomous_Vehicle_2024 Project'::'eRod_Autonomous_Vehicle_2024'::'Physical Architecture'::'Structure'::'Physical System'.'eRod'.'AV Controller'.'PP 2' {
                                @CapellaID { eid = "fd876190-16a4-43d6-a680-4e25f9972ed8"; } 
                                attribute :>> interfaceName = "Network 2"; 
                            }  
                            interface '3569d933-f18c-47e3-b993-0939cc30b22f' : PhysicalLink 
                                connect sourcePhysicalPort ::> 'eRod_Autonomous_Vehicle_2024 Project'::'eRod_Autonomous_Vehicle_2024'::'Physical Architecture'::'Structure'::'Physical System'.'eRod'.'Autonomous Vehicle System'.'Front Camera'.'PP 1'
                                to targetPhysicalPort ::> 'eRod_Autonomous_Vehicle_2024 Project'::'eRod_Autonomous_Vehicle_2024'::'Physical Architecture'::'Structure'::'Physical System'.'eRod'.'AV Controller'.'PP 3' {
                                @CapellaID { eid = "3569d933-f18c-47e3-b993-0939cc30b22f"; } 
                                attribute :>> interfaceName = "Network 1"; 
                            }  
                            interface '94d4a3d9-5442-4873-adbe-ce63760c3718' : PhysicalLink 
                                connect sourcePhysicalPort ::> 'eRod_Autonomous_Vehicle_2024 Project'::'eRod_Autonomous_Vehicle_2024'::'Physical Architecture'::'Structure'::'Physical System'.'eRod'.'Autonomous Vehicle System'.'LIDAR'.'PP 1'
                                to targetPhysicalPort ::> 'eRod_Autonomous_Vehicle_2024 Project'::'eRod_Autonomous_Vehicle_2024'::'Physical Architecture'::'Structure'::'Physical System'.'eRod'.'AV Controller'.'PP 4' {
                                @CapellaID { eid = "94d4a3d9-5442-4873-adbe-ce63760c3718"; } 
                                attribute :>> interfaceName = "Network 5"; 
                            }  
                            interface '55c64ba4-834f-48b7-babe-01291bfdaf5a' : PhysicalLink 
                                connect sourcePhysicalPort ::> 'eRod_Autonomous_Vehicle_2024 Project'::'eRod_Autonomous_Vehicle_2024'::'Physical Architecture'::'Structure'::'Physical System'.'eRod'.'Autonomous Vehicle System'.'Rear Camera'.'PP 1'
                                to targetPhysicalPort ::> 'eRod_Autonomous_Vehicle_2024 Project'::'eRod_Autonomous_Vehicle_2024'::'Physical Architecture'::'Structure'::'Physical System'.'eRod'.'AV Controller'.'PP 5' {
                                @CapellaID { eid = "55c64ba4-834f-48b7-babe-01291bfdaf5a"; } 
                                attribute :>> interfaceName = "Network 4"; 
                            }  
                            ref :>> ownedPhysicalComponents =  ('eRod_Autonomous_Vehicle_2024 Project'::'eRod_Autonomous_Vehicle_2024'::'Physical Architecture'::'Structure'::'Physical System'.'eRod'.'Autonomous Vehicle System'.'Rear Camera',
                            'eRod_Autonomous_Vehicle_2024 Project'::'eRod_Autonomous_Vehicle_2024'::'Physical Architecture'::'Structure'::'Physical System'.'eRod'.'Autonomous Vehicle System'.'Side Camera (Left)',
                            'eRod_Autonomous_Vehicle_2024 Project'::'eRod_Autonomous_Vehicle_2024'::'Physical Architecture'::'Structure'::'Physical System'.'eRod'.'Autonomous Vehicle System'.'Front Camera',
                            'eRod_Autonomous_Vehicle_2024 Project'::'eRod_Autonomous_Vehicle_2024'::'Physical Architecture'::'Structure'::'Physical System'.'eRod'.'Autonomous Vehicle System'.'Side Camera (Right)',
                            'eRod_Autonomous_Vehicle_2024 Project'::'eRod_Autonomous_Vehicle_2024'::'Physical Architecture'::'Structure'::'Physical System'.'eRod'.'Autonomous Vehicle System'.'LIDAR'); 
                            ref :>> ownedPhysicalLinks =  ('eRod_Autonomous_Vehicle_2024 Project'::'eRod_Autonomous_Vehicle_2024'::'Physical Architecture'::'Structure'::'Physical System'.'eRod'.'Autonomous Vehicle System'.'0a17f7b4-0b57-43b8-b516-449a2e74974f',
                            'eRod_Autonomous_Vehicle_2024 Project'::'eRod_Autonomous_Vehicle_2024'::'Physical Architecture'::'Structure'::'Physical System'.'eRod'.'Autonomous Vehicle System'.'fd876190-16a4-43d6-a680-4e25f9972ed8',
                            'eRod_Autonomous_Vehicle_2024 Project'::'eRod_Autonomous_Vehicle_2024'::'Physical Architecture'::'Structure'::'Physical System'.'eRod'.'Autonomous Vehicle System'.'3569d933-f18c-47e3-b993-0939cc30b22f',
                            'eRod_Autonomous_Vehicle_2024 Project'::'eRod_Autonomous_Vehicle_2024'::'Physical Architecture'::'Structure'::'Physical System'.'eRod'.'Autonomous Vehicle System'.'94d4a3d9-5442-4873-adbe-ce63760c3718',
                            'eRod_Autonomous_Vehicle_2024 Project'::'eRod_Autonomous_Vehicle_2024'::'Physical Architecture'::'Structure'::'Physical System'.'eRod'.'Autonomous Vehicle System'.'55c64ba4-834f-48b7-babe-01291bfdaf5a'); 
                        }  
                        part 'Seat sensor Left' : PhysicalComponent { 
                            @CapellaID { eid = "08e61235-93c5-4a3f-b23e-fbac609d5511"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "a6600c80-98e6-4bce-a351-f65cf244071a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Seat Sensor Right' : PhysicalComponent { 
                            @CapellaID { eid = "6c4b2546-4624-42d1-81ea-754f51c9597e"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "13d9b298-ee5e-4142-bcf3-a9a18dbfcc57"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Rear Fog Light Left' : PhysicalComponent { 
                            @CapellaID { eid = "e62e24ef-2b27-49fc-b3d5-e58fc658139a"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "dfe2db41-a1b4-4d96-af67-e762ab878bbc"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Rear Fog Light Rear' : PhysicalComponent { 
                            @CapellaID { eid = "76d53d1b-cb4f-4718-895f-de8ee7b542d1"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "71c44f95-e004-4a0e-b3b0-8887c3cd137f"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Hand Brake' : PhysicalComponent { 
                            @CapellaID { eid = "78e2db1b-cbb8-4424-bb28-e6970a15b03a"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "332fbe57-8cb9-40c0-ae71-7f482ace88a7"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'ePS' : PhysicalComponent { 
                            @CapellaID { eid = "5782d805-c38d-4682-9b07-46115afcb1d7"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "b8574135-5d56-49b5-9743-8a33ed8b8e9a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 2' : PhysicalPort { 
                                @CapellaID { eid = "403d9dc6-0cac-4cde-a037-29f84f6e27a1"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Brake solenoid' : PhysicalComponent { 
                            @CapellaID { eid = "7c85ecd7-a976-4ba4-810f-b770da1fd87c"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "43fba204-8cea-4c25-bfe1-6f0a018ba5ff"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 4' : PhysicalPort { 
                                @CapellaID { eid = "3d3e45e3-4651-4139-9ea8-e26bebe007ed"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Brake Controller' : PhysicalComponent { 
                            @CapellaID { eid = "6c843501-9802-4aa5-9b43-73f6ea5bc4ad"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "2fed07e7-9f06-4383-b7f7-1f1fda3eabc7"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 3' : PhysicalPort { 
                                @CapellaID { eid = "8651787a-4414-4caa-aa6f-89e2c2c28878"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            allocation 'b1c89a08-709a-4aac-bdcb-deb3f41f4940' : PartDeploymentLink
                                allocate deployed ::> 'eRod_Autonomous_Vehicle_2024 Project'::'eRod_Autonomous_Vehicle_2024'::'Physical Architecture'::'Structure'::'Physical System'.'eRod'.'Brake Controller'
                                to deploying ::> 'eRod_Autonomous_Vehicle_2024 Project'::'eRod_Autonomous_Vehicle_2024'::'Physical Architecture'::'Structure'::'Physical System'.'Brake Controller'; 
                        }  
                        part 'Left Steering Knuckle' : PhysicalComponent { 
                            @CapellaID { eid = "cfe02d64-e0af-4243-90af-01fc4f4c6fc5"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "f4c18f1d-0b4e-4b63-ad7b-e1c6514292d2"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '91d6f22c-c105-440c-8a32-fbaa1f7f4388' : ComponentPortAllocation
                                    allocate allocatedPort ::> 'eRod_Autonomous_Vehicle_2024 Project'::'eRod_Autonomous_Vehicle_2024'::'Physical Architecture'::'Structure'::'Physical System'.'eRod'.'Left Steering Knuckle'.'PP 1'
                                    to allocatingPort ::> 'eRod_Autonomous_Vehicle_2024 Project'::'eRod_Autonomous_Vehicle_2024'::'Physical Architecture'::'Structure'::'Physical System'.'LSK'.'CP 1'; 
                                ref :>> ownedComponentPortAllocations =  ('eRod_Autonomous_Vehicle_2024 Project'::'eRod_Autonomous_Vehicle_2024'::'Physical Architecture'::'Structure'::'Physical System'.'eRod'.'Left Steering Knuckle'.'PP 1'.'91d6f22c-c105-440c-8a32-fbaa1f7f4388'); 
                            }  
                            port 'PP 2' : PhysicalPort { 
                                @CapellaID { eid = "25eb6d62-c06e-4fa0-b18e-95186b3c9596"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '1355b84f-9401-4fab-8f55-c1d8335c179c' : ComponentPortAllocation
                                    allocate allocatedPort ::> 'eRod_Autonomous_Vehicle_2024 Project'::'eRod_Autonomous_Vehicle_2024'::'Physical Architecture'::'Structure'::'Physical System'.'eRod'.'Left Steering Knuckle'.'PP 2'
                                    to allocatingPort ::> 'eRod_Autonomous_Vehicle_2024 Project'::'eRod_Autonomous_Vehicle_2024'::'Physical Architecture'::'Structure'::'Physical System'.'LSK'.'CP 2'; 
                                ref :>> ownedComponentPortAllocations =  ('eRod_Autonomous_Vehicle_2024 Project'::'eRod_Autonomous_Vehicle_2024'::'Physical Architecture'::'Structure'::'Physical System'.'eRod'.'Left Steering Knuckle'.'PP 2'.'1355b84f-9401-4fab-8f55-c1d8335c179c'); 
                            }  
                            attribute 'Control_Arm_Mass' : PropertyValueGroup { 
                                @CapellaID { eid = "6e6c3f05-dba4-4da4-b9e4-dcd2ad93c1b2"; } 
                                attribute 'Units' : StringPropertyValue  = 'Kg' { 
                                    @CapellaID { eid = "18725b92-2cac-4a2d-a9a4-9467a8909658"; } 
                                }  
                                attribute 'Value' : FloatPropertyValue  = 1.9 { 
                                    @CapellaID { eid = "dffb5326-3a17-4f11-b386-136229a07b10"; } 
                                }  
                                attribute 'Source' : StringPropertyValue  = 'ER-556' { 
                                    @CapellaID { eid = "7d72a044-3fe8-4c8d-b3c5-cb2bbadc223f"; } 
                                }  
                                ref :>> ownedPropertyValues =  ('eRod_Autonomous_Vehicle_2024 Project'::'eRod_Autonomous_Vehicle_2024'::'Physical Architecture'::'Structure'::'Physical System'.'eRod'.'Left Steering Knuckle'.'Control_Arm_Mass'.'Units',
                                'eRod_Autonomous_Vehicle_2024 Project'::'eRod_Autonomous_Vehicle_2024'::'Physical Architecture'::'Structure'::'Physical System'.'eRod'.'Left Steering Knuckle'.'Control_Arm_Mass'.'Value',
                                'eRod_Autonomous_Vehicle_2024 Project'::'eRod_Autonomous_Vehicle_2024'::'Physical Architecture'::'Structure'::'Physical System'.'eRod'.'Left Steering Knuckle'.'Control_Arm_Mass'.'Source'); 
                                ref :>> appliedPropertyValues =  ('eRod_Autonomous_Vehicle_2024 Project'::'eRod_Autonomous_Vehicle_2024'::'Physical Architecture'::'Structure'::'Physical System'.'eRod'.'Left Steering Knuckle'.'Control_Arm_Mass'.'Units',
                                'eRod_Autonomous_Vehicle_2024 Project'::'eRod_Autonomous_Vehicle_2024'::'Physical Architecture'::'Structure'::'Physical System'.'eRod'.'Left Steering Knuckle'.'Control_Arm_Mass'.'Value',
                                'eRod_Autonomous_Vehicle_2024 Project'::'eRod_Autonomous_Vehicle_2024'::'Physical Architecture'::'Structure'::'Physical System'.'eRod'.'Left Steering Knuckle'.'Control_Arm_Mass'.'Source'); 
                            }  
                            ref :>> ownedPropertyValueGroups =  ('eRod_Autonomous_Vehicle_2024 Project'::'eRod_Autonomous_Vehicle_2024'::'Physical Architecture'::'Structure'::'Physical System'.'eRod'.'Left Steering Knuckle'.'Control_Arm_Mass'); 
                            ref :>> appliedPropertyValueGroups =  ('eRod_Autonomous_Vehicle_2024 Project'::'eRod_Autonomous_Vehicle_2024'::'Physical Architecture'::'Structure'::'Physical System'.'eRod'.'Left Steering Knuckle'.'Control_Arm_Mass'); 
                            allocation '76462ca7-ab16-4c2f-8955-2bf59bcb112e' : PartDeploymentLink
                                allocate deployed ::> 'eRod_Autonomous_Vehicle_2024 Project'::'eRod_Autonomous_Vehicle_2024'::'Physical Architecture'::'Structure'::'Physical System'.'eRod'.'Left Steering Knuckle'
                                to deploying ::> 'eRod_Autonomous_Vehicle_2024 Project'::'eRod_Autonomous_Vehicle_2024'::'Physical Architecture'::'Structure'::'Physical System'.'LSK'; 
                        }  
                        part 'Rack' : PhysicalComponent { 
                            @CapellaID { eid = "b7a772d0-fe81-4f8d-9ced-fefe6595f2c4"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "a2d1df59-e4d1-4df9-a291-824f91c11849"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 2' : PhysicalPort { 
                                @CapellaID { eid = "ebb66b22-bd3b-4495-a20c-82b210b7cf77"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 3' : PhysicalPort { 
                                @CapellaID { eid = "1e7d4a70-00d9-4e38-8668-cafb955b9762"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Right Steering Knuckle' : PhysicalComponent { 
                            @CapellaID { eid = "5e75e505-b727-403b-924a-0b151793dd1b"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "3212bd42-fbe7-432d-8942-7ddcc9ce279d"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '28d419aa-b492-481e-ba9c-4f6d7a3d114e' : ComponentPortAllocation
                                    allocate allocatedPort ::> 'eRod_Autonomous_Vehicle_2024 Project'::'eRod_Autonomous_Vehicle_2024'::'Physical Architecture'::'Structure'::'Physical System'.'eRod'.'Right Steering Knuckle'.'PP 1'
                                    to allocatingPort ::> 'eRod_Autonomous_Vehicle_2024 Project'::'eRod_Autonomous_Vehicle_2024'::'Physical Architecture'::'Structure'::'Physical System'.'RSK'.'SM'; 
                                ref :>> ownedComponentPortAllocations =  ('eRod_Autonomous_Vehicle_2024 Project'::'eRod_Autonomous_Vehicle_2024'::'Physical Architecture'::'Structure'::'Physical System'.'eRod'.'Right Steering Knuckle'.'PP 1'.'28d419aa-b492-481e-ba9c-4f6d7a3d114e'); 
                            }  
                            port 'PP 2' : PhysicalPort { 
                                @CapellaID { eid = "49ce4d2a-4d3d-4049-8de9-6fa9d68e9d54"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'e41ba5c5-bac8-4f65-94f8-4a873b3cc71a' : ComponentPortAllocation
                                    allocate allocatedPort ::> 'eRod_Autonomous_Vehicle_2024 Project'::'eRod_Autonomous_Vehicle_2024'::'Physical Architecture'::'Structure'::'Physical System'.'eRod'.'Right Steering Knuckle'.'PP 2'
                                    to allocatingPort ::> 'eRod_Autonomous_Vehicle_2024 Project'::'eRod_Autonomous_Vehicle_2024'::'Physical Architecture'::'Structure'::'Physical System'.'RSK'.'FRK'; 
                                ref :>> ownedComponentPortAllocations =  ('eRod_Autonomous_Vehicle_2024 Project'::'eRod_Autonomous_Vehicle_2024'::'Physical Architecture'::'Structure'::'Physical System'.'eRod'.'Right Steering Knuckle'.'PP 2'.'e41ba5c5-bac8-4f65-94f8-4a873b3cc71a'); 
                            }  
                            attribute 'Control_Arm_Mass' : PropertyValueGroup { 
                                @CapellaID { eid = "ddf322c4-32a6-4760-844f-c2b8ed9a632a"; } 
                                attribute 'Units' : StringPropertyValue  = 'Kg' { 
                                    @CapellaID { eid = "25479d39-4a7d-46c1-8b74-0b93afe896b2"; } 
                                }  
                                attribute 'Value' : FloatPropertyValue  = 1.9 { 
                                    @CapellaID { eid = "a680c9ff-2b93-4a16-8b5b-7de7a9c81b5b"; } 
                                }  
                                attribute 'Source' : StringPropertyValue  = 'ER-556' { 
                                    @CapellaID { eid = "bfe63488-9755-49c3-9652-61488f72a3a6"; } 
                                }  
                                ref :>> ownedPropertyValues =  ('eRod_Autonomous_Vehicle_2024 Project'::'eRod_Autonomous_Vehicle_2024'::'Physical Architecture'::'Structure'::'Physical System'.'eRod'.'Right Steering Knuckle'.'Control_Arm_Mass'.'Units',
                                'eRod_Autonomous_Vehicle_2024 Project'::'eRod_Autonomous_Vehicle_2024'::'Physical Architecture'::'Structure'::'Physical System'.'eRod'.'Right Steering Knuckle'.'Control_Arm_Mass'.'Value',
                                'eRod_Autonomous_Vehicle_2024 Project'::'eRod_Autonomous_Vehicle_2024'::'Physical Architecture'::'Structure'::'Physical System'.'eRod'.'Right Steering Knuckle'.'Control_Arm_Mass'.'Source'); 
                                ref :>> appliedPropertyValues =  ('eRod_Autonomous_Vehicle_2024 Project'::'eRod_Autonomous_Vehicle_2024'::'Physical Architecture'::'Structure'::'Physical System'.'eRod'.'Right Steering Knuckle'.'Control_Arm_Mass'.'Units',
                                'eRod_Autonomous_Vehicle_2024 Project'::'eRod_Autonomous_Vehicle_2024'::'Physical Architecture'::'Structure'::'Physical System'.'eRod'.'Right Steering Knuckle'.'Control_Arm_Mass'.'Value',
                                'eRod_Autonomous_Vehicle_2024 Project'::'eRod_Autonomous_Vehicle_2024'::'Physical Architecture'::'Structure'::'Physical System'.'eRod'.'Right Steering Knuckle'.'Control_Arm_Mass'.'Source'); 
                            }  
                            ref :>> ownedPropertyValueGroups =  ('eRod_Autonomous_Vehicle_2024 Project'::'eRod_Autonomous_Vehicle_2024'::'Physical Architecture'::'Structure'::'Physical System'.'eRod'.'Right Steering Knuckle'.'Control_Arm_Mass'); 
                            ref :>> appliedPropertyValueGroups =  ('eRod_Autonomous_Vehicle_2024 Project'::'eRod_Autonomous_Vehicle_2024'::'Physical Architecture'::'Structure'::'Physical System'.'eRod'.'Right Steering Knuckle'.'Control_Arm_Mass',
                            'eRod_Autonomous_Vehicle_2024 Project'::'eRod_Autonomous_Vehicle_2024'::'SMW Properties'::'Parameters'::'Mass Range'); 
                            allocation '2b6de427-a11e-481a-b6a2-851f24f5a647' : PartDeploymentLink
                                allocate deployed ::> 'eRod_Autonomous_Vehicle_2024 Project'::'eRod_Autonomous_Vehicle_2024'::'Physical Architecture'::'Structure'::'Physical System'.'eRod'.'Right Steering Knuckle'
                                to deploying ::> 'eRod_Autonomous_Vehicle_2024 Project'::'eRod_Autonomous_Vehicle_2024'::'Physical Architecture'::'Structure'::'Physical System'.'RSK'; 
                        }  
                        part 'Steering Gear' : PhysicalComponent { 
                            @CapellaID { eid = "c4114c2e-177d-4e79-a0c8-5c08187bee03"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "e560ac41-372f-4c5c-95f7-f08aabe95ae9"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 2' : PhysicalPort { 
                                @CapellaID { eid = "df908074-86ac-49e0-bff7-57cffd44cfdc"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 3' : PhysicalPort { 
                                @CapellaID { eid = "758930cb-d450-4a0b-bbf2-3b0844deee82"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Steering Motor' : PhysicalComponent { 
                            @CapellaID { eid = "e69d539c-ff78-4729-8ae8-68f227de99e3"; } 
                            attribute :>> isAbstract = false; 
                            attribute :>> isActor = false; 
                            attribute :>> isHuman = false; 
                            attribute :>> kind = PhysicalComponentKind::HARDWARE; 
                            attribute :>> nature = PhysicalComponentNature::NODE; 
                            port 'SG' : PhysicalPort { 
                                @CapellaID { eid = "8bdd6364-950e-44d0-8c86-61ff36d45ece"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '1c692cf5-b672-47a8-abf8-5b0e70f61ae9' : ComponentPortAllocation
                                    allocate allocatedPort ::> 'eRod_Autonomous_Vehicle_2024 Project'::'eRod_Autonomous_Vehicle_2024'::'Physical Architecture'::'Structure'::'Physical System'.'eRod'.'Steering Motor'.'SG'
                                    to allocatingPort ::> 'eRod_Autonomous_Vehicle_2024 Project'::'eRod_Autonomous_Vehicle_2024'::'Physical Architecture'::'Structure'::'Physical System'.'Motor Controller'.'CP 3'; 
                                ref allocation '9517de80-1e2b-4245-87f8-6fc287814760' : ComponentPortAllocation
                                    allocate allocatedPort ::> 'eRod_Autonomous_Vehicle_2024 Project'::'eRod_Autonomous_Vehicle_2024'::'Physical Architecture'::'Structure'::'Physical System'.'eRod'.'Steering Motor'.'SG'
                                    to allocatingPort ::> 'eRod_Autonomous_Vehicle_2024 Project'::'eRod_Autonomous_Vehicle_2024'::'Physical Architecture'::'Structure'::'Physical System'.'Motor Controller'.'CP 2'; 
                                ref :>> ownedComponentPortAllocations =  ('eRod_Autonomous_Vehicle_2024 Project'::'eRod_Autonomous_Vehicle_2024'::'Physical Architecture'::'Structure'::'Physical System'.'eRod'.'Steering Motor'.'SG'.'1c692cf5-b672-47a8-abf8-5b0e70f61ae9',
                                'eRod_Autonomous_Vehicle_2024 Project'::'eRod_Autonomous_Vehicle_2024'::'Physical Architecture'::'Structure'::'Physical System'.'eRod'.'Steering Motor'.'SG'.'9517de80-1e2b-4245-87f8-6fc287814760'); 
                            }  
                            port 'WG' : PhysicalPort { 
                                @CapellaID { eid = "d81c12f3-bbe3-4057-866f-2ed2bcb3e3d6"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'EPS_C' : PhysicalPort { 
                                @CapellaID { eid = "d2f256eb-0952-49b5-9a19-4ab776ba5570"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '4f096f7c-5b97-4495-a6b8-f96a1d5ee5d3' : ComponentPortAllocation
                                    allocate allocatedPort ::> 'eRod_Autonomous_Vehicle_2024 Project'::'eRod_Autonomous_Vehicle_2024'::'Physical Architecture'::'Structure'::'Physical System'.'eRod'.'Steering Motor'.'EPS_C'
                                    to allocatingPort ::> 'eRod_Autonomous_Vehicle_2024 Project'::'eRod_Autonomous_Vehicle_2024'::'Physical Architecture'::'Structure'::'Physical System'.'Motor Controller'.'CP 1'; 
                                ref :>> ownedComponentPortAllocations =  ('eRod_Autonomous_Vehicle_2024 Project'::'eRod_Autonomous_Vehicle_2024'::'Physical Architecture'::'Structure'::'Physical System'.'eRod'.'Steering Motor'.'EPS_C'.'4f096f7c-5b97-4495-a6b8-f96a1d5ee5d3'); 
                            }  
                            allocation 'e9004703-24f5-4207-8b8c-f417a290cf02' : PartDeploymentLink
                                allocate deployed ::> 'eRod_Autonomous_Vehicle_2024 Project'::'eRod_Autonomous_Vehicle_2024'::'Physical Architecture'::'Structure'::'Physical System'.'eRod'.'Steering Motor'
                                to deploying ::> 'eRod_Autonomous_Vehicle_2024 Project'::'eRod_Autonomous_Vehicle_2024'::'Physical Architecture'::'Structure'::'Physical System'.'Motor Controller'; 
                        }  
                        part 'Steering Wheel' : PhysicalComponent { 
                            @CapellaID { eid = "dff3a2f1-8700-4e30-baa6-a2fbff709ccf"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "dc65328a-aeb0-4041-bda2-f3e27535c9ae"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 2' : PhysicalPort { 
                                @CapellaID { eid = "7545be85-1f45-487e-bf33-6853abb6e40a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'Steering Column' : PhysicalComponent { 
                            doc /*
                            <!DOCTYPE html>
                            <html>
                            <head>
                            <title>Steering Column Description</title>
                            </head>
                            <body>
                            <h1>Steering Column</h1>
                            <p>A steering column is a crucial component in a vehicle's steering system. It connects the steering wheel to the steering mechanism, allowing the driver to control the direction of the vehicle. The primary function of the steering column is to transfer the steering wheel's input to the steering mechanism, enabling the driver to turn the wheels.</p>

                            <p>The structure of a steering column typically consists of several components such as a universal joint, steering shaft, and column housing. The universal joint allows flexibility and compensates for the movement of the steering mechanism. The steering shaft connects the steering wheel to the universal joint, and the column housing provides support and protection for the various internal components.</p>

                            <p>In addition to transferring the driver's input, the steering column may also include other features, such as integrated controls for turn signals, windshield wipers, cruise control, and audio systems. These additional controls enhance the convenience and functionality of the vehicle's steering system.</p>

                            <p>Moreover, modern steering columns often incorporate safety features such as collapsible design. In the event of a frontal collision, a collapsible steering column can absorb impact energy and reduce the risk of injury to the driver. This innovative design has become a standard requirement in automotive safety regulations.</p>

                            <p>Steering columns are designed and engineered to meet specific requirements of different vehicle models. The materials used, manufacturing processes, and overall construction depend on factors such as vehicle type, size, and desired performance. Consequently, steering columns vary in design and features among different manufacturers and models.</p>

                            <h3>References:</h3>
                            <ol>
                            <li>
                            "Column Assembly - Steering." CarParts.com. Accessed February 3, 2022. 
                            <a href="https://www.carparts.com/column-assembly/steering" target="_blank">https://www.carparts.com/column-assembly/steering</a>.
                            </li>
                            <li>
                            "Steering Column." Car Bibles. Accessed February 3, 2022. 
                            <a href="https://www.carbibles.com/steering-column/" target="_blank">https://www.carbibles.com/steering-column/</a>.
                            </li>
                            </ol>

                            </body>
                            </html>
                            */ 
                            @CapellaID { eid = "abad2a4e-de85-4120-a156-17a2316c1eaf"; } 
                            attribute :>> isAbstract = false; 
                            attribute :>> isActor = false; 
                            attribute :>> isHuman = false; 
                            attribute :>> kind = PhysicalComponentKind::HARDWARE; 
                            attribute :>> nature = PhysicalComponentNature::NODE; 
                            part 'Torque Sensor' : PhysicalComponent { 
                                @CapellaID { eid = "e343fbe7-108e-413f-8d93-8b9098f8f114"; } 
                                attribute :>> isAbstract = false; 
                                attribute :>> isActor = false; 
                                attribute :>> isHuman = false; 
                                attribute :>> kind = PhysicalComponentKind::HARDWARE; 
                                attribute :>> nature = PhysicalComponentNature::NODE; 
                                port 'PP 1' : PhysicalPort { 
                                    @CapellaID { eid = "7174b21d-6e23-4f77-b84c-0a956381b26f"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                    ref allocation 'f81ca49a-2bff-4bbd-9325-15a880ba6620' : ComponentPortAllocation
                                        allocate allocatedPort ::> 'eRod_Autonomous_Vehicle_2024 Project'::'eRod_Autonomous_Vehicle_2024'::'Physical Architecture'::'Structure'::'Physical System'.'eRod'.'Steering Column'.'Torque Sensor'.'PP 1'
                                        to allocatingPort ::> 'eRod_Autonomous_Vehicle_2024 Project'::'eRod_Autonomous_Vehicle_2024'::'Physical Architecture'::'Structure'::'Physical System'.'Steer Torque Sensor'.'CP 4'; 
                                    ref :>> ownedComponentPortAllocations =  ('eRod_Autonomous_Vehicle_2024 Project'::'eRod_Autonomous_Vehicle_2024'::'Physical Architecture'::'Structure'::'Physical System'.'eRod'.'Steering Column'.'Torque Sensor'.'PP 1'.'f81ca49a-2bff-4bbd-9325-15a880ba6620'); 
                                }  
                                port 'PP 2' : PhysicalPort { 
                                    @CapellaID { eid = "fb52b715-5f1d-4ac8-8b64-84e8e9ff02dd"; } 
                                    attribute :>> aggregationKind = AggregationKind::UNSET; 
                                    attribute :>> isFinal = false; 
                                    attribute :>> isAbstract = false; 
                                    attribute :>> isDerived = false; 
                                    attribute :>> isPartOfKey = false; 
                                    attribute :>> isReadOnly = false; 
                                    attribute :>> isStatic = false; 
                                    attribute :>> isMaxInclusive = false; 
                                    attribute :>> isMinInclusive = false; 
                                    attribute :>> isOrdered = false; 
                                    attribute :>> isUnique = false; 
                                }  
                                allocation '34ff6da1-2c8c-420d-9856-aec3c200724b' : PartDeploymentLink
                                    allocate deployed ::> 'eRod_Autonomous_Vehicle_2024 Project'::'eRod_Autonomous_Vehicle_2024'::'Physical Architecture'::'Structure'::'Physical System'.'eRod'.'Steering Column'.'Torque Sensor'
                                    to deploying ::> 'eRod_Autonomous_Vehicle_2024 Project'::'eRod_Autonomous_Vehicle_2024'::'Physical Architecture'::'Structure'::'Physical System'.'Steer Torque Sensor'; 
                            }  
                            port 'PP 1' : PhysicalPort { 
                                @CapellaID { eid = "0416f9d6-fa02-4abf-a69d-bccffcc87386"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 2' : PhysicalPort { 
                                @CapellaID { eid = "55aebc62-6b00-4cc9-b29d-4c96356eb743"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 3' : PhysicalPort { 
                                @CapellaID { eid = "8c0a188d-741d-41f5-9175-89f365ca6252"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 4' : PhysicalPort { 
                                @CapellaID { eid = "823b4a9d-e322-40f9-8c8e-8cfc0c70a229"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 6' : PhysicalPort { 
                                @CapellaID { eid = "04ee0d65-86dd-416f-a907-7fad6240b280"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 7' : PhysicalPort { 
                                @CapellaID { eid = "157cfb86-0de9-4f75-a589-c44dc8cde554"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation 'c2a8773a-743b-43a2-b4f8-2b0410021265' : ComponentPortAllocation
                                    allocate allocatedPort ::> 'eRod_Autonomous_Vehicle_2024 Project'::'eRod_Autonomous_Vehicle_2024'::'Physical Architecture'::'Structure'::'Physical System'.'eRod'.'Steering Column'.'PP 7'
                                    to allocatingPort ::> 'eRod_Autonomous_Vehicle_2024 Project'::'eRod_Autonomous_Vehicle_2024'::'Physical Architecture'::'Structure'::'Physical System'.'Steer Torque Sensor'.'CP 1'; 
                                ref :>> ownedComponentPortAllocations =  ('eRod_Autonomous_Vehicle_2024 Project'::'eRod_Autonomous_Vehicle_2024'::'Physical Architecture'::'Structure'::'Physical System'.'eRod'.'Steering Column'.'PP 7'.'c2a8773a-743b-43a2-b4f8-2b0410021265'); 
                            }  
                            interface 'c0f4faf0-5b7e-46ac-82bf-3743bc749ee3' : PhysicalLink 
                                connect sourcePhysicalPort ::> 'eRod_Autonomous_Vehicle_2024 Project'::'eRod_Autonomous_Vehicle_2024'::'Physical Architecture'::'Structure'::'Physical System'.'eRod'.'Steering Column'.'Torque Sensor'.'PP 2'
                                to targetPhysicalPort ::> 'eRod_Autonomous_Vehicle_2024 Project'::'eRod_Autonomous_Vehicle_2024'::'Physical Architecture'::'Structure'::'Physical System'.'eRod'.'Steering Column'.'PP 6' {
                                @CapellaID { eid = "c0f4faf0-5b7e-46ac-82bf-3743bc749ee3"; } 
                                attribute :>> interfaceName = "PL 1"; 
                            }  
                            interface '9eee548b-cbae-4bbf-8d87-ba377861edce' : PhysicalLink 
                                connect sourcePhysicalPort ::> 'eRod_Autonomous_Vehicle_2024 Project'::'eRod_Autonomous_Vehicle_2024'::'Physical Architecture'::'Structure'::'Physical System'.'eRod'.'Steering Column'.'PP 1'
                                to targetPhysicalPort ::> 'eRod_Autonomous_Vehicle_2024 Project'::'eRod_Autonomous_Vehicle_2024'::'Physical Architecture'::'Structure'::'Physical System'.'eRod'.'Steering Column'.'Torque Sensor'.'PP 1' {
                                @CapellaID { eid = "9eee548b-cbae-4bbf-8d87-ba377861edce"; } 
                                attribute :>> interfaceName = "Column Sensor"; 
                            }  
                            ref :>> ownedPhysicalComponents =  ('eRod_Autonomous_Vehicle_2024 Project'::'eRod_Autonomous_Vehicle_2024'::'Physical Architecture'::'Structure'::'Physical System'.'eRod'.'Steering Column'.'Torque Sensor'); 
                            ref :>> ownedPhysicalLinks =  ('eRod_Autonomous_Vehicle_2024 Project'::'eRod_Autonomous_Vehicle_2024'::'Physical Architecture'::'Structure'::'Physical System'.'eRod'.'Steering Column'.'c0f4faf0-5b7e-46ac-82bf-3743bc749ee3',
                            'eRod_Autonomous_Vehicle_2024 Project'::'eRod_Autonomous_Vehicle_2024'::'Physical Architecture'::'Structure'::'Physical System'.'eRod'.'Steering Column'.'9eee548b-cbae-4bbf-8d87-ba377861edce'); 
                        }  
                        part 'Worm Gear' : PhysicalComponent { 
                            @CapellaID { eid = "6d6fc900-8169-407c-bd17-e93e43215e39"; } 
                            attribute :>> isAbstract = false; 
                            attribute :>> isActor = false; 
                            attribute :>> isHuman = false; 
                            attribute :>> kind = PhysicalComponentKind::HARDWARE; 
                            attribute :>> nature = PhysicalComponentNature::NODE; 
                            port 'PP 1' : PhysicalPort { 
                                @CapellaID { eid = "ff860838-4dd6-4be3-b30a-010f9570a420"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 2' : PhysicalPort { 
                                @CapellaID { eid = "971fbc14-c756-4efd-989d-1b022923de67"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                        }  
                        part 'EPS Controller' : PhysicalComponent { 
                            @CapellaID { eid = "2a105f70-fb16-4294-ac8e-bbd7dd6c4ed5"; } 
                            attribute :>> isAbstract = false; 
                            attribute :>> isActor = false; 
                            attribute :>> isHuman = false; 
                            attribute :>> kind = PhysicalComponentKind::UNSET; 
                            attribute :>> nature = PhysicalComponentNature::NODE; 
                            port 'PP 1' : PhysicalPort { 
                                @CapellaID { eid = "9568046b-9e69-45a0-a445-6c95e1775c5c"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '9193e6d0-c720-4e6f-8449-801224ec1ac6' : ComponentPortAllocation
                                    allocate allocatedPort ::> 'eRod_Autonomous_Vehicle_2024 Project'::'eRod_Autonomous_Vehicle_2024'::'Physical Architecture'::'Structure'::'Physical System'.'eRod'.'EPS Controller'.'PP 1'
                                    to allocatingPort ::> 'eRod_Autonomous_Vehicle_2024 Project'::'eRod_Autonomous_Vehicle_2024'::'Physical Architecture'::'Structure'::'Physical System'.'EPS Controller'.'CP 3'; 
                                ref :>> ownedComponentPortAllocations =  ('eRod_Autonomous_Vehicle_2024 Project'::'eRod_Autonomous_Vehicle_2024'::'Physical Architecture'::'Structure'::'Physical System'.'eRod'.'EPS Controller'.'PP 1'.'9193e6d0-c720-4e6f-8449-801224ec1ac6'); 
                            }  
                            port 'PP 2' : PhysicalPort { 
                                @CapellaID { eid = "1179dd30-890f-42e7-8835-ae5bce509bac"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                                ref allocation '8f2da6b2-5f2d-403a-9e78-624118e36fe5' : ComponentPortAllocation
                                    allocate allocatedPort ::> 'eRod_Autonomous_Vehicle_2024 Project'::'eRod_Autonomous_Vehicle_2024'::'Physical Architecture'::'Structure'::'Physical System'.'eRod'.'EPS Controller'.'PP 2'
                                    to allocatingPort ::> 'eRod_Autonomous_Vehicle_2024 Project'::'eRod_Autonomous_Vehicle_2024'::'Physical Architecture'::'Structure'::'Physical System'.'EPS Controller'.'CP 4'; 
                                ref :>> ownedComponentPortAllocations =  ('eRod_Autonomous_Vehicle_2024 Project'::'eRod_Autonomous_Vehicle_2024'::'Physical Architecture'::'Structure'::'Physical System'.'eRod'.'EPS Controller'.'PP 2'.'8f2da6b2-5f2d-403a-9e78-624118e36fe5'); 
                            }  
                            allocation '2a56ce09-ea58-4735-81f5-7ca223a56eea' : PartDeploymentLink
                                allocate deployed ::> 'eRod_Autonomous_Vehicle_2024 Project'::'eRod_Autonomous_Vehicle_2024'::'Physical Architecture'::'Structure'::'Physical System'.'eRod'.'EPS Controller'
                                to deploying ::> 'eRod_Autonomous_Vehicle_2024 Project'::'eRod_Autonomous_Vehicle_2024'::'Physical Architecture'::'Structure'::'Physical System'.'EPS Controller'; 
                        }  
                        part 'Electric Motor' : PhysicalComponent { 
                            @CapellaID { eid = "89aaf29b-c8d4-46ad-a2ef-9097cdb4d7cf"; } 
                            attribute :>> isAbstract = false; 
                            attribute :>> isActor = false; 
                            attribute :>> isHuman = false; 
                            attribute :>> kind = PhysicalComponentKind::HARDWARE; 
                            attribute :>> nature = PhysicalComponentNature::NODE; 
                        }  
                        part 'AV Controller' : PhysicalComponent { 
                            @CapellaID { eid = "62c8e896-7931-4bcf-b882-1bb81b673d67"; } 
                            attribute :>> isAbstract = false; 
                            attribute :>> isActor = false; 
                            attribute :>> isHuman = false; 
                            attribute :>> kind = PhysicalComponentKind::UNSET; 
                            attribute :>> nature = PhysicalComponentNature::NODE; 
                            part 'Battery' : PhysicalComponent { 
                                @CapellaID { eid = "d9d50614-0ac0-4a5c-ada9-f59df0fb7eff"; } 
                                attribute :>> isAbstract = false; 
                                attribute :>> isActor = false; 
                                attribute :>> isHuman = false; 
                                attribute :>> kind = PhysicalComponentKind::HARDWARE; 
                                attribute :>> nature = PhysicalComponentNature::NODE; 
                            }  
                            port 'PP 1' : PhysicalPort { 
                                @CapellaID { eid = "e495ef59-1ba9-47bc-a8f8-8e9e2bfa9bf4"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 2' : PhysicalPort { 
                                @CapellaID { eid = "33fc2c0e-600f-4531-883e-2065a4f8e4bf"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 3' : PhysicalPort { 
                                @CapellaID { eid = "bf4f66e2-b7db-43d7-bd5a-874e8b42df90"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 4' : PhysicalPort { 
                                @CapellaID { eid = "07c33553-2f15-4304-bf9a-959c1dceadb8"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 5' : PhysicalPort { 
                                @CapellaID { eid = "8c9e68ff-e811-4667-8803-0d5e59e2d27a"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 6' : PhysicalPort { 
                                @CapellaID { eid = "e206a6e9-cfec-43fb-a833-9aa87a19e5ff"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            port 'PP 7' : PhysicalPort { 
                                @CapellaID { eid = "fdc64bba-78fb-4960-85d6-4f24fbd58f82"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> isMaxInclusive = false; 
                                attribute :>> isMinInclusive = false; 
                                attribute :>> isOrdered = false; 
                                attribute :>> isUnique = false; 
                            }  
                            ref :>> ownedPhysicalComponents =  ('eRod_Autonomous_Vehicle_2024 Project'::'eRod_Autonomous_Vehicle_2024'::'Physical Architecture'::'Structure'::'Physical System'.'eRod'.'AV Controller'.'Battery'); 
                            allocation '0695b288-249a-40c4-8d29-7ce10c45e27c' : PartDeploymentLink
                                allocate deployed ::> 'eRod_Autonomous_Vehicle_2024 Project'::'eRod_Autonomous_Vehicle_2024'::'Physical Architecture'::'Structure'::'Physical System'.'eRod'.'AV Controller'
                                to deploying ::> 'eRod_Autonomous_Vehicle_2024 Project'::'eRod_Autonomous_Vehicle_2024'::'Physical Architecture'::'Structure'::'Physical System'.'AV Controller'; 
                            allocation 'a7d2b718-7f65-40e7-8faf-76f50176d352' : PartDeploymentLink
                                allocate deployed ::> 'eRod_Autonomous_Vehicle_2024 Project'::'eRod_Autonomous_Vehicle_2024'::'Physical Architecture'::'Structure'::'Physical System'.'eRod'.'AV Controller'
                                to deploying ::> 'eRod_Autonomous_Vehicle_2024 Project'::'eRod_Autonomous_Vehicle_2024'::'Physical Architecture'::'Structure'::'Physical System'.'Perception '; 
                            allocation '31ba48b9-94b0-4f69-9519-efb668e7c58f' : PartDeploymentLink
                                allocate deployed ::> 'eRod_Autonomous_Vehicle_2024 Project'::'eRod_Autonomous_Vehicle_2024'::'Physical Architecture'::'Structure'::'Physical System'.'eRod'.'AV Controller'
                                to deploying ::> 'eRod_Autonomous_Vehicle_2024 Project'::'eRod_Autonomous_Vehicle_2024'::'Physical Architecture'::'Structure'::'Physical System'.'Autonomous Vehicle (AV) System'.'Drive'; 
                            allocation 'f7519273-e5bc-44bc-b239-32f3ff109d3c' : PartDeploymentLink
                                allocate deployed ::> 'eRod_Autonomous_Vehicle_2024 Project'::'eRod_Autonomous_Vehicle_2024'::'Physical Architecture'::'Structure'::'Physical System'.'eRod'.'AV Controller'
                                to deploying ::> 'eRod_Autonomous_Vehicle_2024 Project'::'eRod_Autonomous_Vehicle_2024'::'Physical Architecture'::'Structure'::'Physical System'.'Autonomous Vehicle (AV) System'.'Perception'; 
                        }  
                        interface '8246a27f-08de-491b-94a0-fe1af0539da7' : PhysicalLink 
                            connect sourcePhysicalPort ::> 'eRod_Autonomous_Vehicle_2024 Project'::'eRod_Autonomous_Vehicle_2024'::'Physical Architecture'::'Structure'::'Physical System'.'eRod'.'Left Wheel Carrier'.'PP 1'
                            to targetPhysicalPort ::> 'eRod_Autonomous_Vehicle_2024 Project'::'eRod_Autonomous_Vehicle_2024'::'Physical Architecture'::'Structure'::'Physical System'.'eRod'.'Rear Left Wheel'.'PP 1' {
                            @CapellaID { eid = "8246a27f-08de-491b-94a0-fe1af0539da7"; } 
                            attribute :>> interfaceName = "Wheel Bults"; 
                        }  
                        interface 'd3b81018-1738-42e6-b2af-ee8a591779ff' : PhysicalLink 
                            connect sourcePhysicalPort ::> 'eRod_Autonomous_Vehicle_2024 Project'::'eRod_Autonomous_Vehicle_2024'::'Physical Architecture'::'Structure'::'Physical System'.'eRod'.'Right Wheel Carrier'.'PP 1'
                            to targetPhysicalPort ::> 'eRod_Autonomous_Vehicle_2024 Project'::'eRod_Autonomous_Vehicle_2024'::'Physical Architecture'::'Structure'::'Physical System'.'eRod'.'Rear Right Wheel'.'PP 1' {
                            @CapellaID { eid = "d3b81018-1738-42e6-b2af-ee8a591779ff"; } 
                            attribute :>> interfaceName = "Wheel Bults"; 
                        }  
                        interface 'ba689b2c-7db1-4171-85dc-662047e36409' : PhysicalLink 
                            connect sourcePhysicalPort ::> 'eRod_Autonomous_Vehicle_2024 Project'::'eRod_Autonomous_Vehicle_2024'::'Physical Architecture'::'Structure'::'Physical System'.'eRod'.'Power Train'.'Right Drive Shaft'.'PP 2'
                            to targetPhysicalPort ::> 'eRod_Autonomous_Vehicle_2024 Project'::'eRod_Autonomous_Vehicle_2024'::'Physical Architecture'::'Structure'::'Physical System'.'eRod'.'Right Wheel Carrier'.'PP 2' {
                            @CapellaID { eid = "ba689b2c-7db1-4171-85dc-662047e36409"; } 
                            attribute :>> interfaceName = "Wheel Bearing"; 
                        }  
                        interface '364bad80-25ec-499e-9aad-0ce63d564b08' : PhysicalLink 
                            connect sourcePhysicalPort ::> 'eRod_Autonomous_Vehicle_2024 Project'::'eRod_Autonomous_Vehicle_2024'::'Physical Architecture'::'Structure'::'Physical System'.'eRod'.'Power Train'.'Left Drive Shaft'.'PP 2'
                            to targetPhysicalPort ::> 'eRod_Autonomous_Vehicle_2024 Project'::'eRod_Autonomous_Vehicle_2024'::'Physical Architecture'::'Structure'::'Physical System'.'eRod'.'Left Wheel Carrier'.'PP 2' {
                            @CapellaID { eid = "364bad80-25ec-499e-9aad-0ce63d564b08"; } 
                            attribute :>> interfaceName = "Wheel Beering"; 
                        }  
                        interface 'feb9b337-7955-4ed4-9a54-d354dae872b4' : PhysicalLink 
                            connect sourcePhysicalPort ::> 'eRod_Autonomous_Vehicle_2024 Project'::'eRod_Autonomous_Vehicle_2024'::'Physical Architecture'::'Structure'::'Physical System'.'eRod'.'Horn'.'PP 1'
                            to targetPhysicalPort ::> 'eRod_Autonomous_Vehicle_2024 Project'::'eRod_Autonomous_Vehicle_2024'::'Physical Architecture'::'Structure'::'Physical System'.'eRod'.'Electrical Box Front'.'Horn' {
                            @CapellaID { eid = "feb9b337-7955-4ed4-9a54-d354dae872b4"; } 
                            attribute :>> interfaceName = "EL"; 
                        }  
                        interface '44a95d1c-85c3-4164-8285-9f73c0e34b17' : PhysicalLink 
                            connect sourcePhysicalPort ::> 'eRod_Autonomous_Vehicle_2024 Project'::'eRod_Autonomous_Vehicle_2024'::'Physical Architecture'::'Structure'::'Physical System'.'eRod'.'Power Train'.'Electrical Box Rear'.'Number Plate'
                            to targetPhysicalPort ::> 'eRod_Autonomous_Vehicle_2024 Project'::'eRod_Autonomous_Vehicle_2024'::'Physical Architecture'::'Structure'::'Physical System'.'eRod'.'Number Plate Lights'.'PP 1' {
                            @CapellaID { eid = "44a95d1c-85c3-4164-8285-9f73c0e34b17"; } 
                            attribute :>> interfaceName = "EL"; 
                        }  
                        interface 'c4c55e57-b531-47d5-b3f4-ae1ec6e03a0b' : PhysicalLink 
                            connect sourcePhysicalPort ::> 'eRod_Autonomous_Vehicle_2024 Project'::'eRod_Autonomous_Vehicle_2024'::'Physical Architecture'::'Structure'::'Physical System'.'eRod'.'Power Train'.'Electrical Box Rear'.'Fan'
                            to targetPhysicalPort ::> 'eRod_Autonomous_Vehicle_2024 Project'::'eRod_Autonomous_Vehicle_2024'::'Physical Architecture'::'Structure'::'Physical System'.'eRod'.'Fan'.'PP 1' {
                            @CapellaID { eid = "c4c55e57-b531-47d5-b3f4-ae1ec6e03a0b"; } 
                            attribute :>> interfaceName = "EL"; 
                        }  
                        interface '68a073e6-dca8-4eb9-94a5-765267571421' : PhysicalLink 
                            connect sourcePhysicalPort ::> 'eRod_Autonomous_Vehicle_2024 Project'::'eRod_Autonomous_Vehicle_2024'::'Physical Architecture'::'Structure'::'Physical System'.'eRod'.'Right Rear Light'.'PP 1'
                            to targetPhysicalPort ::> 'eRod_Autonomous_Vehicle_2024 Project'::'eRod_Autonomous_Vehicle_2024'::'Physical Architecture'::'Structure'::'Physical System'.'eRod'.'Power Train'.'Electrical Box Rear'.'Right Rear Lights' {
                            @CapellaID { eid = "68a073e6-dca8-4eb9-94a5-765267571421"; } 
                            attribute :>> interfaceName = "EL"; 
                        }  
                        interface '75189a1e-06e7-4b55-84aa-1bff41418eba' : PhysicalLink 
                            connect sourcePhysicalPort ::> 'eRod_Autonomous_Vehicle_2024 Project'::'eRod_Autonomous_Vehicle_2024'::'Physical Architecture'::'Structure'::'Physical System'.'eRod'.'Right Rear Light w Indicator'.'PP 1'
                            to targetPhysicalPort ::> 'eRod_Autonomous_Vehicle_2024 Project'::'eRod_Autonomous_Vehicle_2024'::'Physical Architecture'::'Structure'::'Physical System'.'eRod'.'Power Train'.'Electrical Box Rear'.'Right Rear Lights' {
                            @CapellaID { eid = "75189a1e-06e7-4b55-84aa-1bff41418eba"; } 
                            attribute :>> interfaceName = "EL"; 
                        }  
                        interface 'be9ed696-dba9-402b-a5e5-2b995ed4b9e3' : PhysicalLink 
                            connect sourcePhysicalPort ::> 'eRod_Autonomous_Vehicle_2024 Project'::'eRod_Autonomous_Vehicle_2024'::'Physical Architecture'::'Structure'::'Physical System'.'eRod'.'Left Rear Light'.'PP 1'
                            to targetPhysicalPort ::> 'eRod_Autonomous_Vehicle_2024 Project'::'eRod_Autonomous_Vehicle_2024'::'Physical Architecture'::'Structure'::'Physical System'.'eRod'.'Power Train'.'Electrical Box Rear'.'Left Rear Lights' {
                            @CapellaID { eid = "be9ed696-dba9-402b-a5e5-2b995ed4b9e3"; } 
                            attribute :>> interfaceName = "EL"; 
                        }  
                        interface 'effb05bc-b993-4f5d-b919-23618a1ac8a8' : PhysicalLink 
                            connect sourcePhysicalPort ::> 'eRod_Autonomous_Vehicle_2024 Project'::'eRod_Autonomous_Vehicle_2024'::'Physical Architecture'::'Structure'::'Physical System'.'eRod'.'Left Rear Light w Indicator'.'PP 1'
                            to targetPhysicalPort ::> 'eRod_Autonomous_Vehicle_2024 Project'::'eRod_Autonomous_Vehicle_2024'::'Physical Architecture'::'Structure'::'Physical System'.'eRod'.'Power Train'.'Electrical Box Rear'.'Left Rear Lights' {
                            @CapellaID { eid = "effb05bc-b993-4f5d-b919-23618a1ac8a8"; } 
                            attribute :>> interfaceName = "EL"; 
                        }  
                        interface 'd6a21aad-a28c-48b0-b9df-e74e5338a3e2' : PhysicalLink 
                            connect sourcePhysicalPort ::> 'eRod_Autonomous_Vehicle_2024 Project'::'eRod_Autonomous_Vehicle_2024'::'Physical Architecture'::'Structure'::'Physical System'.'eRod'.'Electrical Box Front'.'Emergency Switch'
                            to targetPhysicalPort ::> 'eRod_Autonomous_Vehicle_2024 Project'::'eRod_Autonomous_Vehicle_2024'::'Physical Architecture'::'Structure'::'Physical System'.'eRod'.'Dashboard'.'Emergency Off Switch'.'PP 1' {
                            @CapellaID { eid = "d6a21aad-a28c-48b0-b9df-e74e5338a3e2"; } 
                            attribute :>> interfaceName = "EL"; 
                        }  
                        interface '51b07a0e-4257-4680-998a-ec4a2d229e3a' : PhysicalLink 
                            connect sourcePhysicalPort ::> 'eRod_Autonomous_Vehicle_2024 Project'::'eRod_Autonomous_Vehicle_2024'::'Physical Architecture'::'Structure'::'Physical System'.'eRod'.'Electrical Box Front'.'Hazard Light Switch'
                            to targetPhysicalPort ::> 'eRod_Autonomous_Vehicle_2024 Project'::'eRod_Autonomous_Vehicle_2024'::'Physical Architecture'::'Structure'::'Physical System'.'eRod'.'Dashboard'.'Hazard Light Switch'.'PP 1' {
                            @CapellaID { eid = "51b07a0e-4257-4680-998a-ec4a2d229e3a"; } 
                            attribute :>> interfaceName = "EL"; 
                        }  
                        interface '6a146cd9-a276-4626-95d5-608bce715960' : PhysicalLink 
                            connect sourcePhysicalPort ::> 'eRod_Autonomous_Vehicle_2024 Project'::'eRod_Autonomous_Vehicle_2024'::'Physical Architecture'::'Structure'::'Physical System'.'eRod'.'Electrical Box Front'.'Direction Switch'
                            to targetPhysicalPort ::> 'eRod_Autonomous_Vehicle_2024 Project'::'eRod_Autonomous_Vehicle_2024'::'Physical Architecture'::'Structure'::'Physical System'.'eRod'.'Dashboard'.'Driving Direction Switch'.'PP 1' {
                            @CapellaID { eid = "6a146cd9-a276-4626-95d5-608bce715960"; } 
                            attribute :>> interfaceName = "EL"; 
                        }  
                        interface 'c8c3283e-9ac6-4e1a-b198-5ab4fbb1ee40' : PhysicalLink 
                            connect sourcePhysicalPort ::> 'eRod_Autonomous_Vehicle_2024 Project'::'eRod_Autonomous_Vehicle_2024'::'Physical Architecture'::'Structure'::'Physical System'.'eRod'.'Electrical Box Front'.'Light Switch'
                            to targetPhysicalPort ::> 'eRod_Autonomous_Vehicle_2024 Project'::'eRod_Autonomous_Vehicle_2024'::'Physical Architecture'::'Structure'::'Physical System'.'eRod'.'Dashboard'.'High Beam Switch'.'PP 1' {
                            @CapellaID { eid = "c8c3283e-9ac6-4e1a-b198-5ab4fbb1ee40"; } 
                            attribute :>> interfaceName = "EL"; 
                        }  
                        interface '764583df-0c52-452a-8470-f8013f169d22' : PhysicalLink 
                            connect sourcePhysicalPort ::> 'eRod_Autonomous_Vehicle_2024 Project'::'eRod_Autonomous_Vehicle_2024'::'Physical Architecture'::'Structure'::'Physical System'.'eRod'.'Electrical Box Front'.'Lights Right'
                            to targetPhysicalPort ::> 'eRod_Autonomous_Vehicle_2024 Project'::'eRod_Autonomous_Vehicle_2024'::'Physical Architecture'::'Structure'::'Physical System'.'eRod'.'Right Side Light'.'PP 2' {
                            @CapellaID { eid = "764583df-0c52-452a-8470-f8013f169d22"; } 
                            attribute :>> interfaceName = "EL"; 
                        }  
                        interface 'c449d887-245d-4074-b422-f0a87cada0d5' : PhysicalLink 
                            connect sourcePhysicalPort ::> 'eRod_Autonomous_Vehicle_2024 Project'::'eRod_Autonomous_Vehicle_2024'::'Physical Architecture'::'Structure'::'Physical System'.'eRod'.'Electrical Box Front'.'Lights Right'
                            to targetPhysicalPort ::> 'eRod_Autonomous_Vehicle_2024 Project'::'eRod_Autonomous_Vehicle_2024'::'Physical Architecture'::'Structure'::'Physical System'.'eRod'.'Right Indicator Light'.'PP 1' {
                            @CapellaID { eid = "c449d887-245d-4074-b422-f0a87cada0d5"; } 
                            attribute :>> interfaceName = "EL"; 
                        }  
                        interface '6b1cd9c8-7a53-4496-bc94-caa1a09694aa' : PhysicalLink 
                            connect sourcePhysicalPort ::> 'eRod_Autonomous_Vehicle_2024 Project'::'eRod_Autonomous_Vehicle_2024'::'Physical Architecture'::'Structure'::'Physical System'.'eRod'.'Electrical Box Front'.'Lights Left'
                            to targetPhysicalPort ::> 'eRod_Autonomous_Vehicle_2024 Project'::'eRod_Autonomous_Vehicle_2024'::'Physical Architecture'::'Structure'::'Physical System'.'eRod'.'Left Side LIght'.'PP 1' {
                            @CapellaID { eid = "6b1cd9c8-7a53-4496-bc94-caa1a09694aa"; } 
                            attribute :>> interfaceName = "EL"; 
                        }  
                        interface 'f9130cb0-5b2b-4450-971b-90641c011a9a' : PhysicalLink 
                            connect sourcePhysicalPort ::> 'eRod_Autonomous_Vehicle_2024 Project'::'eRod_Autonomous_Vehicle_2024'::'Physical Architecture'::'Structure'::'Physical System'.'eRod'.'Electrical Box Front'.'Lights Left'
                            to targetPhysicalPort ::> 'eRod_Autonomous_Vehicle_2024 Project'::'eRod_Autonomous_Vehicle_2024'::'Physical Architecture'::'Structure'::'Physical System'.'eRod'.'Left Indicator Light'.'PP 1' {
                            @CapellaID { eid = "f9130cb0-5b2b-4450-971b-90641c011a9a"; } 
                            attribute :>> interfaceName = "EL"; 
                        }  
                        interface 'a64b7bbf-96e6-460b-93eb-bbc2d078dc2e' : PhysicalLink 
                            connect sourcePhysicalPort ::> 'eRod_Autonomous_Vehicle_2024 Project'::'eRod_Autonomous_Vehicle_2024'::'Physical Architecture'::'Structure'::'Physical System'.'eRod'.'Electrical Box Front'.'Lights Left'
                            to targetPhysicalPort ::> 'eRod_Autonomous_Vehicle_2024 Project'::'eRod_Autonomous_Vehicle_2024'::'Physical Architecture'::'Structure'::'Physical System'.'eRod'.'Left High-Beam Light'.'PP 1' {
                            @CapellaID { eid = "a64b7bbf-96e6-460b-93eb-bbc2d078dc2e"; } 
                            attribute :>> interfaceName = "EL"; 
                        }  
                        interface '2c8b2fb6-5f49-44bd-86b4-1680a104e4d1' : PhysicalLink 
                            connect sourcePhysicalPort ::> 'eRod_Autonomous_Vehicle_2024 Project'::'eRod_Autonomous_Vehicle_2024'::'Physical Architecture'::'Structure'::'Physical System'.'eRod'.'Electrical Box Front'.'Lights Left'
                            to targetPhysicalPort ::> 'eRod_Autonomous_Vehicle_2024 Project'::'eRod_Autonomous_Vehicle_2024'::'Physical Architecture'::'Structure'::'Physical System'.'eRod'.'Left Low-Beam Light'.'PP 1' {
                            @CapellaID { eid = "2c8b2fb6-5f49-44bd-86b4-1680a104e4d1"; } 
                            attribute :>> interfaceName = "EL"; 
                        }  
                        interface 'cd510f89-2936-44b0-ab85-a96ef1bf63e3' : PhysicalLink 
                            connect sourcePhysicalPort ::> 'eRod_Autonomous_Vehicle_2024 Project'::'eRod_Autonomous_Vehicle_2024'::'Physical Architecture'::'Structure'::'Physical System'.'eRod'.'Electrical Box Front'.'Lights Right'
                            to targetPhysicalPort ::> 'eRod_Autonomous_Vehicle_2024 Project'::'eRod_Autonomous_Vehicle_2024'::'Physical Architecture'::'Structure'::'Physical System'.'eRod'.'Right Low-Beam Light'.'PP 1' {
                            @CapellaID { eid = "cd510f89-2936-44b0-ab85-a96ef1bf63e3"; } 
                            attribute :>> interfaceName = "EL"; 
                        }  
                        interface 'e489e56f-1ef8-49a0-9e2f-c364d023646c' : PhysicalLink 
                            connect sourcePhysicalPort ::> 'eRod_Autonomous_Vehicle_2024 Project'::'eRod_Autonomous_Vehicle_2024'::'Physical Architecture'::'Structure'::'Physical System'.'eRod'.'Electrical Box Front'.'Lights Right'
                            to targetPhysicalPort ::> 'eRod_Autonomous_Vehicle_2024 Project'::'eRod_Autonomous_Vehicle_2024'::'Physical Architecture'::'Structure'::'Physical System'.'eRod'.'Right High-Beam Light'.'PP 1' {
                            @CapellaID { eid = "e489e56f-1ef8-49a0-9e2f-c364d023646c"; } 
                            attribute :>> interfaceName = "EL"; 
                        }  
                        interface '393fceb5-bc09-4404-b136-220afd97a119' : PhysicalLink 
                            connect sourcePhysicalPort ::> 'eRod_Autonomous_Vehicle_2024 Project'::'eRod_Autonomous_Vehicle_2024'::'Physical Architecture'::'Structure'::'Physical System'.'eRod'.'Gas Pedal'.'PP 1'
                            to targetPhysicalPort ::> 'eRod_Autonomous_Vehicle_2024 Project'::'eRod_Autonomous_Vehicle_2024'::'Physical Architecture'::'Structure'::'Physical System'.'eRod'.'Power Train'.'Electrical Box Rear'.'Accelerator Pedal' {
                            @CapellaID { eid = "393fceb5-bc09-4404-b136-220afd97a119"; } 
                            attribute :>> interfaceName = "EL"; 
                        }  
                        interface '70b6d737-eeb5-487e-81eb-6b5f02bf928c' : PhysicalLink 
                            connect sourcePhysicalPort ::> 'eRod_Autonomous_Vehicle_2024 Project'::'eRod_Autonomous_Vehicle_2024'::'Physical Architecture'::'Structure'::'Physical System'.'eRod'.'Brake Pedal'.'PP 1'
                            to targetPhysicalPort ::> 'eRod_Autonomous_Vehicle_2024 Project'::'eRod_Autonomous_Vehicle_2024'::'Physical Architecture'::'Structure'::'Physical System'.'eRod'.'Electrical Box Front'.'Brake Pedal' {
                            @CapellaID { eid = "70b6d737-eeb5-487e-81eb-6b5f02bf928c"; } 
                            attribute :>> interfaceName = "EL"; 
                        }  
                        interface '5c9569a7-6f09-4422-b75f-edff4149a722' : PhysicalLink 
                            connect sourcePhysicalPort ::> 'eRod_Autonomous_Vehicle_2024 Project'::'eRod_Autonomous_Vehicle_2024'::'Physical Architecture'::'Structure'::'Physical System'.'eRod'.'Dashboard'.'Ignition Lock'.'PP 1'
                            to targetPhysicalPort ::> 'eRod_Autonomous_Vehicle_2024 Project'::'eRod_Autonomous_Vehicle_2024'::'Physical Architecture'::'Structure'::'Physical System'.'eRod'.'Electrical Box Front'.'Ignition Lock' {
                            @CapellaID { eid = "5c9569a7-6f09-4422-b75f-edff4149a722"; } 
                            attribute :>> interfaceName = "EL"; 
                        }  
                        interface '59bcb856-bbb6-4e83-a269-9a53a5de8266' : PhysicalLink 
                            connect sourcePhysicalPort ::> 'eRod_Autonomous_Vehicle_2024 Project'::'eRod_Autonomous_Vehicle_2024'::'Physical Architecture'::'Structure'::'Physical System'.'eRod'.'Dashboard'.'Indicator Switch'.'PP 1'
                            to targetPhysicalPort ::> 'eRod_Autonomous_Vehicle_2024 Project'::'eRod_Autonomous_Vehicle_2024'::'Physical Architecture'::'Structure'::'Physical System'.'eRod'.'Electrical Box Front'.'Indicator' {
                            @CapellaID { eid = "59bcb856-bbb6-4e83-a269-9a53a5de8266"; } 
                            attribute :>> interfaceName = "EL"; 
                        }  
                        interface 'ab70a5c0-0665-441e-aeeb-bd06436697cd' : PhysicalLink 
                            connect sourcePhysicalPort ::> 'eRod_Autonomous_Vehicle_2024 Project'::'eRod_Autonomous_Vehicle_2024'::'Physical Architecture'::'Structure'::'Physical System'.'eRod'.'Display'.'PP 1'
                            to targetPhysicalPort ::> 'eRod_Autonomous_Vehicle_2024 Project'::'eRod_Autonomous_Vehicle_2024'::'Physical Architecture'::'Structure'::'Physical System'.'eRod'.'Power Train'.'Electrical Box Rear'.'Display' {
                            @CapellaID { eid = "ab70a5c0-0665-441e-aeeb-bd06436697cd"; } 
                            attribute :>> interfaceName = "EL"; 
                        }  
                        interface '73c4e008-7a5b-4240-bf35-ca02c1f5bb0c' : PhysicalLink 
                            connect sourcePhysicalPort ::> 'eRod_Autonomous_Vehicle_2024 Project'::'eRod_Autonomous_Vehicle_2024'::'Physical Architecture'::'Structure'::'Physical System'.'eRod'.'Electrical Box Front'.'Rear Electrical Box'
                            to targetPhysicalPort ::> 'eRod_Autonomous_Vehicle_2024 Project'::'eRod_Autonomous_Vehicle_2024'::'Physical Architecture'::'Structure'::'Physical System'.'eRod'.'Power Train'.'Electrical Box Rear'.'Front Electrical Box' {
                            @CapellaID { eid = "73c4e008-7a5b-4240-bf35-ca02c1f5bb0c"; } 
                            attribute :>> interfaceName = "EL"; 
                        }  
                        interface 'b1abe57f-7274-45ad-af5e-ef152c3a6ddd' : PhysicalLink 
                            connect sourcePhysicalPort ::> 'eRod_Autonomous_Vehicle_2024 Project'::'eRod_Autonomous_Vehicle_2024'::'Physical Architecture'::'Structure'::'Physical System'.'eRod'.'Rack'.'PP 1'
                            to targetPhysicalPort ::> 'eRod_Autonomous_Vehicle_2024 Project'::'eRod_Autonomous_Vehicle_2024'::'Physical Architecture'::'Structure'::'Physical System'.'eRod'.'Left Steering Knuckle'.'PP 1' {
                            @CapellaID { eid = "b1abe57f-7274-45ad-af5e-ef152c3a6ddd"; } 
                            attribute :>> interfaceName = "Tie Rod"; 
                        }  
                        interface '98933770-96de-4dc4-9d5e-e12daf26af1a' : PhysicalLink 
                            connect sourcePhysicalPort ::> 'eRod_Autonomous_Vehicle_2024 Project'::'eRod_Autonomous_Vehicle_2024'::'Physical Architecture'::'Structure'::'Physical System'.'eRod'.'Rack'.'PP 2'
                            to targetPhysicalPort ::> 'eRod_Autonomous_Vehicle_2024 Project'::'eRod_Autonomous_Vehicle_2024'::'Physical Architecture'::'Structure'::'Physical System'.'eRod'.'Right Steering Knuckle'.'PP 1' {
                            @CapellaID { eid = "98933770-96de-4dc4-9d5e-e12daf26af1a"; } 
                            attribute :>> interfaceName = "Tie Rod"; 
                        }  
                        interface '2a47616f-bd9d-4835-8171-b4f272501f48' : PhysicalLink 
                            connect sourcePhysicalPort ::> 'eRod_Autonomous_Vehicle_2024 Project'::'eRod_Autonomous_Vehicle_2024'::'Physical Architecture'::'Structure'::'Physical System'.'eRod'.'Steering Gear'.'PP 1'
                            to targetPhysicalPort ::> 'eRod_Autonomous_Vehicle_2024 Project'::'eRod_Autonomous_Vehicle_2024'::'Physical Architecture'::'Structure'::'Physical System'.'eRod'.'Rack'.'PP 3' {
                            @CapellaID { eid = "2a47616f-bd9d-4835-8171-b4f272501f48"; } 
                            attribute :>> interfaceName = "Pinion"; 
                        }  
                        interface 'c8d59d0e-69fb-41de-acd3-8261ed75d0be' : PhysicalLink 
                            connect sourcePhysicalPort ::> 'eRod_Autonomous_Vehicle_2024 Project'::'eRod_Autonomous_Vehicle_2024'::'Physical Architecture'::'Structure'::'Physical System'.'eRod'.'Steering Wheel'.'PP 1'
                            to targetPhysicalPort ::> 'eRod_Autonomous_Vehicle_2024 Project'::'eRod_Autonomous_Vehicle_2024'::'Physical Architecture'::'Structure'::'Physical System'.'eRod'.'Steering Column'.'PP 1' {
                            @CapellaID { eid = "c8d59d0e-69fb-41de-acd3-8261ed75d0be"; } 
                            attribute :>> interfaceName = "Steering Wheel Nut"; 
                        }  
                        interface '62ff6a70-53f2-4594-b115-1f651997afac' : PhysicalLink 
                            connect sourcePhysicalPort ::> 'eRod_Autonomous_Vehicle_2024 Project'::'eRod_Autonomous_Vehicle_2024'::'Physical Architecture'::'Structure'::'Physical System'.'eRod'.'Steering Column'.'PP 2'
                            to targetPhysicalPort ::> 'eRod_Autonomous_Vehicle_2024 Project'::'eRod_Autonomous_Vehicle_2024'::'Physical Architecture'::'Structure'::'Physical System'.'eRod'.'Steering Gear'.'PP 2' {
                            @CapellaID { eid = "62ff6a70-53f2-4594-b115-1f651997afac"; } 
                            attribute :>> interfaceName = "Mech"; 
                        }  
                        interface '4c3c727f-b164-4d36-80bf-5527901bd677' : PhysicalLink 
                            connect sourcePhysicalPort ::> 'eRod_Autonomous_Vehicle_2024 Project'::'eRod_Autonomous_Vehicle_2024'::'Physical Architecture'::'Structure'::'Physical System'.'eRod'.'Steering Motor'.'SG'
                            to targetPhysicalPort ::> 'eRod_Autonomous_Vehicle_2024 Project'::'eRod_Autonomous_Vehicle_2024'::'Physical Architecture'::'Structure'::'Physical System'.'eRod'.'Steering Gear'.'PP 3' {
                            @CapellaID { eid = "4c3c727f-b164-4d36-80bf-5527901bd677"; } 
                            attribute :>> interfaceName = "Mech"; 
                        }  
                        interface '02d3f587-95a5-4448-bdeb-bfe778232db2' : PhysicalLink 
                            connect sourcePhysicalPort ::> 'eRod_Autonomous_Vehicle_2024 Project'::'eRod_Autonomous_Vehicle_2024'::'Physical Architecture'::'Structure'::'Physical System'.'eRod'.'Power Train'.'Electrical Box Rear'.'Seat Sensor Left'
                            to targetPhysicalPort ::> 'eRod_Autonomous_Vehicle_2024 Project'::'eRod_Autonomous_Vehicle_2024'::'Physical Architecture'::'Structure'::'Physical System'.'eRod'.'Seat sensor Left'.'PP 1' {
                            @CapellaID { eid = "02d3f587-95a5-4448-bdeb-bfe778232db2"; } 
                            attribute :>> interfaceName = "Seat Sensor Left"; 
                        }  
                        interface 'a1a29c70-3d60-4002-a916-9e830f4f059e' : PhysicalLink 
                            connect sourcePhysicalPort ::> 'eRod_Autonomous_Vehicle_2024 Project'::'eRod_Autonomous_Vehicle_2024'::'Physical Architecture'::'Structure'::'Physical System'.'eRod'.'Power Train'.'Electrical Box Rear'.'Seat Sensor Right'
                            to targetPhysicalPort ::> 'eRod_Autonomous_Vehicle_2024 Project'::'eRod_Autonomous_Vehicle_2024'::'Physical Architecture'::'Structure'::'Physical System'.'eRod'.'Seat Sensor Right'.'PP 1' {
                            @CapellaID { eid = "a1a29c70-3d60-4002-a916-9e830f4f059e"; } 
                            attribute :>> interfaceName = "Seat Sensor Right"; 
                        }  
                        interface '04d8c169-f4ac-4335-806a-a79969ce935f' : PhysicalLink 
                            connect sourcePhysicalPort ::> 'eRod_Autonomous_Vehicle_2024 Project'::'eRod_Autonomous_Vehicle_2024'::'Physical Architecture'::'Structure'::'Physical System'.'eRod'.'Power Train'.'Electrical Box Rear'.'Rear Fog Light Left'
                            to targetPhysicalPort ::> 'eRod_Autonomous_Vehicle_2024 Project'::'eRod_Autonomous_Vehicle_2024'::'Physical Architecture'::'Structure'::'Physical System'.'eRod'.'Rear Fog Light Left'.'PP 1' {
                            @CapellaID { eid = "04d8c169-f4ac-4335-806a-a79969ce935f"; } 
                            attribute :>> interfaceName = "EL"; 
                        }  
                        interface '11c44a24-c5aa-48a8-a115-df65bc4846b0' : PhysicalLink 
                            connect sourcePhysicalPort ::> 'eRod_Autonomous_Vehicle_2024 Project'::'eRod_Autonomous_Vehicle_2024'::'Physical Architecture'::'Structure'::'Physical System'.'eRod'.'Power Train'.'Electrical Box Rear'.'Rear Fog Light Right'
                            to targetPhysicalPort ::> 'eRod_Autonomous_Vehicle_2024 Project'::'eRod_Autonomous_Vehicle_2024'::'Physical Architecture'::'Structure'::'Physical System'.'eRod'.'Rear Fog Light Rear'.'PP 1' {
                            @CapellaID { eid = "11c44a24-c5aa-48a8-a115-df65bc4846b0"; } 
                            attribute :>> interfaceName = "EL"; 
                        }  
                        interface 'cdff8d06-3ce0-492f-ba47-94391cf21d1c' : PhysicalLink 
                            connect sourcePhysicalPort ::> 'eRod_Autonomous_Vehicle_2024 Project'::'eRod_Autonomous_Vehicle_2024'::'Physical Architecture'::'Structure'::'Physical System'.'eRod'.'Power Train'.'Electrical Box Rear'.'Hand Brake'
                            to targetPhysicalPort ::> 'eRod_Autonomous_Vehicle_2024 Project'::'eRod_Autonomous_Vehicle_2024'::'Physical Architecture'::'Structure'::'Physical System'.'eRod'.'Hand Brake'.'PP 1' {
                            @CapellaID { eid = "cdff8d06-3ce0-492f-ba47-94391cf21d1c"; } 
                            attribute :>> interfaceName = "EL"; 
                        }  
                        interface '3d9af7a4-0a48-4747-80fd-9e6e91e37d43' : PhysicalLink 
                            connect sourcePhysicalPort ::> 'eRod_Autonomous_Vehicle_2024 Project'::'eRod_Autonomous_Vehicle_2024'::'Physical Architecture'::'Structure'::'Physical System'.'eRod'.'ePS'.'PP 1'
                            to targetPhysicalPort ::> 'eRod_Autonomous_Vehicle_2024 Project'::'eRod_Autonomous_Vehicle_2024'::'Physical Architecture'::'Structure'::'Physical System'.'eRod'.'Steering Column'.'PP 3' {
                            @CapellaID { eid = "3d9af7a4-0a48-4747-80fd-9e6e91e37d43"; } 
                            attribute :>> interfaceName = "Mech"; 
                        }  
                        interface '5f82fb7c-46cb-4b71-8450-120391351d20' : PhysicalLink 
                            connect sourcePhysicalPort ::> 'eRod_Autonomous_Vehicle_2024 Project'::'eRod_Autonomous_Vehicle_2024'::'Physical Architecture'::'Structure'::'Physical System'.'eRod'.'ePS'.'PP 2'
                            to targetPhysicalPort ::> 'eRod_Autonomous_Vehicle_2024 Project'::'eRod_Autonomous_Vehicle_2024'::'Physical Architecture'::'Structure'::'Physical System'.'eRod'.'AV Controller'.'PP 6' {
                            @CapellaID { eid = "5f82fb7c-46cb-4b71-8450-120391351d20"; } 
                            attribute :>> interfaceName = "EL"; 
                        }  
                        interface 'a994705f-aade-445e-ba41-512bc3285feb' : PhysicalLink 
                            connect sourcePhysicalPort ::> 'eRod_Autonomous_Vehicle_2024 Project'::'eRod_Autonomous_Vehicle_2024'::'Physical Architecture'::'Structure'::'Physical System'.'eRod'.'Worm Gear'.'PP 1'
                            to targetPhysicalPort ::> 'eRod_Autonomous_Vehicle_2024 Project'::'eRod_Autonomous_Vehicle_2024'::'Physical Architecture'::'Structure'::'Physical System'.'eRod'.'Steering Column'.'PP 4' {
                            @CapellaID { eid = "a994705f-aade-445e-ba41-512bc3285feb"; } 
                            attribute :>> interfaceName = "MECH"; 
                        }  
                        interface 'f0b37d85-81b8-4b2b-9fcb-da2c66033a40' : PhysicalLink 
                            connect sourcePhysicalPort ::> 'eRod_Autonomous_Vehicle_2024 Project'::'eRod_Autonomous_Vehicle_2024'::'Physical Architecture'::'Structure'::'Physical System'.'eRod'.'Front Left Wheel'.'PP 3'
                            to targetPhysicalPort ::> 'eRod_Autonomous_Vehicle_2024 Project'::'eRod_Autonomous_Vehicle_2024'::'Physical Architecture'::'Structure'::'Physical System'.'eRod'.'Left Steering Knuckle'.'PP 2' {
                            @CapellaID { eid = "f0b37d85-81b8-4b2b-9fcb-da2c66033a40"; } 
                            attribute :>> interfaceName = "PL 44"; 
                        }  
                        interface '4bb604e9-5ce3-43d1-b61a-241b07ab0d56' : PhysicalLink 
                            connect sourcePhysicalPort ::> 'eRod_Autonomous_Vehicle_2024 Project'::'eRod_Autonomous_Vehicle_2024'::'Physical Architecture'::'Structure'::'Physical System'.'eRod'.'Front Right Wheel'.'PP 2'
                            to targetPhysicalPort ::> 'eRod_Autonomous_Vehicle_2024 Project'::'eRod_Autonomous_Vehicle_2024'::'Physical Architecture'::'Structure'::'Physical System'.'eRod'.'Right Steering Knuckle'.'PP 2' {
                            @CapellaID { eid = "4bb604e9-5ce3-43d1-b61a-241b07ab0d56"; } 
                            attribute :>> interfaceName = "M RSK - FRW"; 
                        }  
                        ref :>> ownedPhysicalComponents =  ('eRod_Autonomous_Vehicle_2024 Project'::'eRod_Autonomous_Vehicle_2024'::'Physical Architecture'::'Structure'::'Physical System'.'eRod'.'Power Train',
                        'eRod_Autonomous_Vehicle_2024 Project'::'eRod_Autonomous_Vehicle_2024'::'Physical Architecture'::'Structure'::'Physical System'.'eRod'.'Front Left Wheel',
                        'eRod_Autonomous_Vehicle_2024 Project'::'eRod_Autonomous_Vehicle_2024'::'Physical Architecture'::'Structure'::'Physical System'.'eRod'.'Front Right Wheel',
                        'eRod_Autonomous_Vehicle_2024 Project'::'eRod_Autonomous_Vehicle_2024'::'Physical Architecture'::'Structure'::'Physical System'.'eRod'.'Rear Left Wheel',
                        'eRod_Autonomous_Vehicle_2024 Project'::'eRod_Autonomous_Vehicle_2024'::'Physical Architecture'::'Structure'::'Physical System'.'eRod'.'Rear Right Wheel',
                        'eRod_Autonomous_Vehicle_2024 Project'::'eRod_Autonomous_Vehicle_2024'::'Physical Architecture'::'Structure'::'Physical System'.'eRod'.'Left Wheel Carrier',
                        'eRod_Autonomous_Vehicle_2024 Project'::'eRod_Autonomous_Vehicle_2024'::'Physical Architecture'::'Structure'::'Physical System'.'eRod'.'Right Wheel Carrier',
                        'eRod_Autonomous_Vehicle_2024 Project'::'eRod_Autonomous_Vehicle_2024'::'Physical Architecture'::'Structure'::'Physical System'.'eRod'.'Electrical Box Front',
                        'eRod_Autonomous_Vehicle_2024 Project'::'eRod_Autonomous_Vehicle_2024'::'Physical Architecture'::'Structure'::'Physical System'.'eRod'.'Horn',
                        'eRod_Autonomous_Vehicle_2024 Project'::'eRod_Autonomous_Vehicle_2024'::'Physical Architecture'::'Structure'::'Physical System'.'eRod'.'Dashboard',
                        'eRod_Autonomous_Vehicle_2024 Project'::'eRod_Autonomous_Vehicle_2024'::'Physical Architecture'::'Structure'::'Physical System'.'eRod'.'Fan',
                        'eRod_Autonomous_Vehicle_2024 Project'::'eRod_Autonomous_Vehicle_2024'::'Physical Architecture'::'Structure'::'Physical System'.'eRod'.'Left High-Beam Light',
                        'eRod_Autonomous_Vehicle_2024 Project'::'eRod_Autonomous_Vehicle_2024'::'Physical Architecture'::'Structure'::'Physical System'.'eRod'.'Right High-Beam Light',
                        'eRod_Autonomous_Vehicle_2024 Project'::'eRod_Autonomous_Vehicle_2024'::'Physical Architecture'::'Structure'::'Physical System'.'eRod'.'Left Low-Beam Light',
                        'eRod_Autonomous_Vehicle_2024 Project'::'eRod_Autonomous_Vehicle_2024'::'Physical Architecture'::'Structure'::'Physical System'.'eRod'.'Right Low-Beam Light',
                        'eRod_Autonomous_Vehicle_2024 Project'::'eRod_Autonomous_Vehicle_2024'::'Physical Architecture'::'Structure'::'Physical System'.'eRod'.'Left Indicator Light',
                        'eRod_Autonomous_Vehicle_2024 Project'::'eRod_Autonomous_Vehicle_2024'::'Physical Architecture'::'Structure'::'Physical System'.'eRod'.'Right Indicator Light',
                        'eRod_Autonomous_Vehicle_2024 Project'::'eRod_Autonomous_Vehicle_2024'::'Physical Architecture'::'Structure'::'Physical System'.'eRod'.'Left Rear Light w Indicator',
                        'eRod_Autonomous_Vehicle_2024 Project'::'eRod_Autonomous_Vehicle_2024'::'Physical Architecture'::'Structure'::'Physical System'.'eRod'.'Left Rear Light',
                        'eRod_Autonomous_Vehicle_2024 Project'::'eRod_Autonomous_Vehicle_2024'::'Physical Architecture'::'Structure'::'Physical System'.'eRod'.'Right Rear Light',
                        'eRod_Autonomous_Vehicle_2024 Project'::'eRod_Autonomous_Vehicle_2024'::'Physical Architecture'::'Structure'::'Physical System'.'eRod'.'Right Rear Light w Indicator',
                        'eRod_Autonomous_Vehicle_2024 Project'::'eRod_Autonomous_Vehicle_2024'::'Physical Architecture'::'Structure'::'Physical System'.'eRod'.'Number Plate Lights',
                        'eRod_Autonomous_Vehicle_2024 Project'::'eRod_Autonomous_Vehicle_2024'::'Physical Architecture'::'Structure'::'Physical System'.'eRod'.'Left Side LIght',
                        'eRod_Autonomous_Vehicle_2024 Project'::'eRod_Autonomous_Vehicle_2024'::'Physical Architecture'::'Structure'::'Physical System'.'eRod'.'Right Side Light',
                        'eRod_Autonomous_Vehicle_2024 Project'::'eRod_Autonomous_Vehicle_2024'::'Physical Architecture'::'Structure'::'Physical System'.'eRod'.'Charger',
                        'eRod_Autonomous_Vehicle_2024 Project'::'eRod_Autonomous_Vehicle_2024'::'Physical Architecture'::'Structure'::'Physical System'.'eRod'.'Gas Pedal',
                        'eRod_Autonomous_Vehicle_2024 Project'::'eRod_Autonomous_Vehicle_2024'::'Physical Architecture'::'Structure'::'Physical System'.'eRod'.'Brake Pedal',
                        'eRod_Autonomous_Vehicle_2024 Project'::'eRod_Autonomous_Vehicle_2024'::'Physical Architecture'::'Structure'::'Physical System'.'eRod'.'Display',
                        'eRod_Autonomous_Vehicle_2024 Project'::'eRod_Autonomous_Vehicle_2024'::'Physical Architecture'::'Structure'::'Physical System'.'eRod'.'Brakes',
                        'eRod_Autonomous_Vehicle_2024 Project'::'eRod_Autonomous_Vehicle_2024'::'Physical Architecture'::'Structure'::'Physical System'.'eRod'.'Autonomous Vehicle System',
                        'eRod_Autonomous_Vehicle_2024 Project'::'eRod_Autonomous_Vehicle_2024'::'Physical Architecture'::'Structure'::'Physical System'.'eRod'.'Seat sensor Left',
                        'eRod_Autonomous_Vehicle_2024 Project'::'eRod_Autonomous_Vehicle_2024'::'Physical Architecture'::'Structure'::'Physical System'.'eRod'.'Seat Sensor Right',
                        'eRod_Autonomous_Vehicle_2024 Project'::'eRod_Autonomous_Vehicle_2024'::'Physical Architecture'::'Structure'::'Physical System'.'eRod'.'Rear Fog Light Left',
                        'eRod_Autonomous_Vehicle_2024 Project'::'eRod_Autonomous_Vehicle_2024'::'Physical Architecture'::'Structure'::'Physical System'.'eRod'.'Rear Fog Light Rear',
                        'eRod_Autonomous_Vehicle_2024 Project'::'eRod_Autonomous_Vehicle_2024'::'Physical Architecture'::'Structure'::'Physical System'.'eRod'.'Hand Brake',
                        'eRod_Autonomous_Vehicle_2024 Project'::'eRod_Autonomous_Vehicle_2024'::'Physical Architecture'::'Structure'::'Physical System'.'eRod'.'ePS',
                        'eRod_Autonomous_Vehicle_2024 Project'::'eRod_Autonomous_Vehicle_2024'::'Physical Architecture'::'Structure'::'Physical System'.'eRod'.'Brake solenoid',
                        'eRod_Autonomous_Vehicle_2024 Project'::'eRod_Autonomous_Vehicle_2024'::'Physical Architecture'::'Structure'::'Physical System'.'eRod'.'Brake Controller',
                        'eRod_Autonomous_Vehicle_2024 Project'::'eRod_Autonomous_Vehicle_2024'::'Physical Architecture'::'Structure'::'Physical System'.'eRod'.'Left Steering Knuckle',
                        'eRod_Autonomous_Vehicle_2024 Project'::'eRod_Autonomous_Vehicle_2024'::'Physical Architecture'::'Structure'::'Physical System'.'eRod'.'Rack',
                        'eRod_Autonomous_Vehicle_2024 Project'::'eRod_Autonomous_Vehicle_2024'::'Physical Architecture'::'Structure'::'Physical System'.'eRod'.'Right Steering Knuckle',
                        'eRod_Autonomous_Vehicle_2024 Project'::'eRod_Autonomous_Vehicle_2024'::'Physical Architecture'::'Structure'::'Physical System'.'eRod'.'Steering Gear',
                        'eRod_Autonomous_Vehicle_2024 Project'::'eRod_Autonomous_Vehicle_2024'::'Physical Architecture'::'Structure'::'Physical System'.'eRod'.'Steering Motor',
                        'eRod_Autonomous_Vehicle_2024 Project'::'eRod_Autonomous_Vehicle_2024'::'Physical Architecture'::'Structure'::'Physical System'.'eRod'.'Steering Wheel',
                        'eRod_Autonomous_Vehicle_2024 Project'::'eRod_Autonomous_Vehicle_2024'::'Physical Architecture'::'Structure'::'Physical System'.'eRod'.'Steering Column',
                        'eRod_Autonomous_Vehicle_2024 Project'::'eRod_Autonomous_Vehicle_2024'::'Physical Architecture'::'Structure'::'Physical System'.'eRod'.'Worm Gear',
                        'eRod_Autonomous_Vehicle_2024 Project'::'eRod_Autonomous_Vehicle_2024'::'Physical Architecture'::'Structure'::'Physical System'.'eRod'.'EPS Controller',
                        'eRod_Autonomous_Vehicle_2024 Project'::'eRod_Autonomous_Vehicle_2024'::'Physical Architecture'::'Structure'::'Physical System'.'eRod'.'Electric Motor',
                        'eRod_Autonomous_Vehicle_2024 Project'::'eRod_Autonomous_Vehicle_2024'::'Physical Architecture'::'Structure'::'Physical System'.'eRod'.'AV Controller'); 
                         
                        ref :>> ownedPhysicalLinks =  ('eRod_Autonomous_Vehicle_2024 Project'::'eRod_Autonomous_Vehicle_2024'::'Physical Architecture'::'Structure'::'Physical System'.'eRod'.'8246a27f-08de-491b-94a0-fe1af0539da7',
                        'eRod_Autonomous_Vehicle_2024 Project'::'eRod_Autonomous_Vehicle_2024'::'Physical Architecture'::'Structure'::'Physical System'.'eRod'.'d3b81018-1738-42e6-b2af-ee8a591779ff',
                        'eRod_Autonomous_Vehicle_2024 Project'::'eRod_Autonomous_Vehicle_2024'::'Physical Architecture'::'Structure'::'Physical System'.'eRod'.'ba689b2c-7db1-4171-85dc-662047e36409',
                        'eRod_Autonomous_Vehicle_2024 Project'::'eRod_Autonomous_Vehicle_2024'::'Physical Architecture'::'Structure'::'Physical System'.'eRod'.'364bad80-25ec-499e-9aad-0ce63d564b08',
                        'eRod_Autonomous_Vehicle_2024 Project'::'eRod_Autonomous_Vehicle_2024'::'Physical Architecture'::'Structure'::'Physical System'.'eRod'.'feb9b337-7955-4ed4-9a54-d354dae872b4',
                        'eRod_Autonomous_Vehicle_2024 Project'::'eRod_Autonomous_Vehicle_2024'::'Physical Architecture'::'Structure'::'Physical System'.'eRod'.'44a95d1c-85c3-4164-8285-9f73c0e34b17',
                        'eRod_Autonomous_Vehicle_2024 Project'::'eRod_Autonomous_Vehicle_2024'::'Physical Architecture'::'Structure'::'Physical System'.'eRod'.'c4c55e57-b531-47d5-b3f4-ae1ec6e03a0b',
                        'eRod_Autonomous_Vehicle_2024 Project'::'eRod_Autonomous_Vehicle_2024'::'Physical Architecture'::'Structure'::'Physical System'.'eRod'.'68a073e6-dca8-4eb9-94a5-765267571421',
                        'eRod_Autonomous_Vehicle_2024 Project'::'eRod_Autonomous_Vehicle_2024'::'Physical Architecture'::'Structure'::'Physical System'.'eRod'.'75189a1e-06e7-4b55-84aa-1bff41418eba',
                        'eRod_Autonomous_Vehicle_2024 Project'::'eRod_Autonomous_Vehicle_2024'::'Physical Architecture'::'Structure'::'Physical System'.'eRod'.'be9ed696-dba9-402b-a5e5-2b995ed4b9e3',
                        'eRod_Autonomous_Vehicle_2024 Project'::'eRod_Autonomous_Vehicle_2024'::'Physical Architecture'::'Structure'::'Physical System'.'eRod'.'effb05bc-b993-4f5d-b919-23618a1ac8a8',
                        'eRod_Autonomous_Vehicle_2024 Project'::'eRod_Autonomous_Vehicle_2024'::'Physical Architecture'::'Structure'::'Physical System'.'eRod'.'d6a21aad-a28c-48b0-b9df-e74e5338a3e2',
                        'eRod_Autonomous_Vehicle_2024 Project'::'eRod_Autonomous_Vehicle_2024'::'Physical Architecture'::'Structure'::'Physical System'.'eRod'.'51b07a0e-4257-4680-998a-ec4a2d229e3a',
                        'eRod_Autonomous_Vehicle_2024 Project'::'eRod_Autonomous_Vehicle_2024'::'Physical Architecture'::'Structure'::'Physical System'.'eRod'.'6a146cd9-a276-4626-95d5-608bce715960',
                        'eRod_Autonomous_Vehicle_2024 Project'::'eRod_Autonomous_Vehicle_2024'::'Physical Architecture'::'Structure'::'Physical System'.'eRod'.'c8c3283e-9ac6-4e1a-b198-5ab4fbb1ee40',
                        'eRod_Autonomous_Vehicle_2024 Project'::'eRod_Autonomous_Vehicle_2024'::'Physical Architecture'::'Structure'::'Physical System'.'eRod'.'764583df-0c52-452a-8470-f8013f169d22',
                        'eRod_Autonomous_Vehicle_2024 Project'::'eRod_Autonomous_Vehicle_2024'::'Physical Architecture'::'Structure'::'Physical System'.'eRod'.'c449d887-245d-4074-b422-f0a87cada0d5',
                        'eRod_Autonomous_Vehicle_2024 Project'::'eRod_Autonomous_Vehicle_2024'::'Physical Architecture'::'Structure'::'Physical System'.'eRod'.'6b1cd9c8-7a53-4496-bc94-caa1a09694aa',
                        'eRod_Autonomous_Vehicle_2024 Project'::'eRod_Autonomous_Vehicle_2024'::'Physical Architecture'::'Structure'::'Physical System'.'eRod'.'f9130cb0-5b2b-4450-971b-90641c011a9a',
                        'eRod_Autonomous_Vehicle_2024 Project'::'eRod_Autonomous_Vehicle_2024'::'Physical Architecture'::'Structure'::'Physical System'.'eRod'.'a64b7bbf-96e6-460b-93eb-bbc2d078dc2e',
                        'eRod_Autonomous_Vehicle_2024 Project'::'eRod_Autonomous_Vehicle_2024'::'Physical Architecture'::'Structure'::'Physical System'.'eRod'.'2c8b2fb6-5f49-44bd-86b4-1680a104e4d1',
                        'eRod_Autonomous_Vehicle_2024 Project'::'eRod_Autonomous_Vehicle_2024'::'Physical Architecture'::'Structure'::'Physical System'.'eRod'.'cd510f89-2936-44b0-ab85-a96ef1bf63e3',
                        'eRod_Autonomous_Vehicle_2024 Project'::'eRod_Autonomous_Vehicle_2024'::'Physical Architecture'::'Structure'::'Physical System'.'eRod'.'e489e56f-1ef8-49a0-9e2f-c364d023646c',
                        'eRod_Autonomous_Vehicle_2024 Project'::'eRod_Autonomous_Vehicle_2024'::'Physical Architecture'::'Structure'::'Physical System'.'eRod'.'393fceb5-bc09-4404-b136-220afd97a119',
                        'eRod_Autonomous_Vehicle_2024 Project'::'eRod_Autonomous_Vehicle_2024'::'Physical Architecture'::'Structure'::'Physical System'.'eRod'.'70b6d737-eeb5-487e-81eb-6b5f02bf928c',
                        'eRod_Autonomous_Vehicle_2024 Project'::'eRod_Autonomous_Vehicle_2024'::'Physical Architecture'::'Structure'::'Physical System'.'eRod'.'5c9569a7-6f09-4422-b75f-edff4149a722',
                        'eRod_Autonomous_Vehicle_2024 Project'::'eRod_Autonomous_Vehicle_2024'::'Physical Architecture'::'Structure'::'Physical System'.'eRod'.'59bcb856-bbb6-4e83-a269-9a53a5de8266',
                        'eRod_Autonomous_Vehicle_2024 Project'::'eRod_Autonomous_Vehicle_2024'::'Physical Architecture'::'Structure'::'Physical System'.'eRod'.'ab70a5c0-0665-441e-aeeb-bd06436697cd',
                        'eRod_Autonomous_Vehicle_2024 Project'::'eRod_Autonomous_Vehicle_2024'::'Physical Architecture'::'Structure'::'Physical System'.'eRod'.'73c4e008-7a5b-4240-bf35-ca02c1f5bb0c',
                        'eRod_Autonomous_Vehicle_2024 Project'::'eRod_Autonomous_Vehicle_2024'::'Physical Architecture'::'Structure'::'Physical System'.'eRod'.'b1abe57f-7274-45ad-af5e-ef152c3a6ddd',
                        'eRod_Autonomous_Vehicle_2024 Project'::'eRod_Autonomous_Vehicle_2024'::'Physical Architecture'::'Structure'::'Physical System'.'eRod'.'98933770-96de-4dc4-9d5e-e12daf26af1a',
                        'eRod_Autonomous_Vehicle_2024 Project'::'eRod_Autonomous_Vehicle_2024'::'Physical Architecture'::'Structure'::'Physical System'.'eRod'.'2a47616f-bd9d-4835-8171-b4f272501f48',
                        'eRod_Autonomous_Vehicle_2024 Project'::'eRod_Autonomous_Vehicle_2024'::'Physical Architecture'::'Structure'::'Physical System'.'eRod'.'c8d59d0e-69fb-41de-acd3-8261ed75d0be',
                        'eRod_Autonomous_Vehicle_2024 Project'::'eRod_Autonomous_Vehicle_2024'::'Physical Architecture'::'Structure'::'Physical System'.'eRod'.'62ff6a70-53f2-4594-b115-1f651997afac',
                        'eRod_Autonomous_Vehicle_2024 Project'::'eRod_Autonomous_Vehicle_2024'::'Physical Architecture'::'Structure'::'Physical System'.'eRod'.'4c3c727f-b164-4d36-80bf-5527901bd677',
                        'eRod_Autonomous_Vehicle_2024 Project'::'eRod_Autonomous_Vehicle_2024'::'Physical Architecture'::'Structure'::'Physical System'.'eRod'.'02d3f587-95a5-4448-bdeb-bfe778232db2',
                        'eRod_Autonomous_Vehicle_2024 Project'::'eRod_Autonomous_Vehicle_2024'::'Physical Architecture'::'Structure'::'Physical System'.'eRod'.'a1a29c70-3d60-4002-a916-9e830f4f059e',
                        'eRod_Autonomous_Vehicle_2024 Project'::'eRod_Autonomous_Vehicle_2024'::'Physical Architecture'::'Structure'::'Physical System'.'eRod'.'04d8c169-f4ac-4335-806a-a79969ce935f',
                        'eRod_Autonomous_Vehicle_2024 Project'::'eRod_Autonomous_Vehicle_2024'::'Physical Architecture'::'Structure'::'Physical System'.'eRod'.'11c44a24-c5aa-48a8-a115-df65bc4846b0',
                        'eRod_Autonomous_Vehicle_2024 Project'::'eRod_Autonomous_Vehicle_2024'::'Physical Architecture'::'Structure'::'Physical System'.'eRod'.'cdff8d06-3ce0-492f-ba47-94391cf21d1c',
                        'eRod_Autonomous_Vehicle_2024 Project'::'eRod_Autonomous_Vehicle_2024'::'Physical Architecture'::'Structure'::'Physical System'.'eRod'.'3d9af7a4-0a48-4747-80fd-9e6e91e37d43',
                        'eRod_Autonomous_Vehicle_2024 Project'::'eRod_Autonomous_Vehicle_2024'::'Physical Architecture'::'Structure'::'Physical System'.'eRod'.'5f82fb7c-46cb-4b71-8450-120391351d20',
                        'eRod_Autonomous_Vehicle_2024 Project'::'eRod_Autonomous_Vehicle_2024'::'Physical Architecture'::'Structure'::'Physical System'.'eRod'.'a994705f-aade-445e-ba41-512bc3285feb',
                        'eRod_Autonomous_Vehicle_2024 Project'::'eRod_Autonomous_Vehicle_2024'::'Physical Architecture'::'Structure'::'Physical System'.'eRod'.'f0b37d85-81b8-4b2b-9fcb-da2c66033a40',
                        'eRod_Autonomous_Vehicle_2024 Project'::'eRod_Autonomous_Vehicle_2024'::'Physical Architecture'::'Structure'::'Physical System'.'eRod'.'4bb604e9-5ce3-43d1-b61a-241b07ab0d56'); 
                    }  
                    part 'Steer Torque Sensor' : PhysicalComponent { 
                        doc /*
                        Certainly! Here's a formal HTML table for a Steer Torque Sensor:

                        ```html
                        <!DOCTYPE html>
                        <html>
                        <head>
                          <title>Steer Torque Sensor Functions</title>
                          <style>
                            table {
                              border-collapse: collapse;
                              width: 100%;
                            }
                            th, td {
                              border: 1px solid black;
                              padding: 8px;
                              text-align: left;
                            }
                            th {
                              background-color: #f2f2f2;
                            }
                          </style>
                        </head>
                        <body>
                          <h1>Steer Torque Sensor Functions</h1>
                          <table>
                            <tr>
                              <th>Function</th>
                              <th>Summary</th>
                              <th>Inputs</th>
                              <th>Outputs</th>
                            </tr>
                            <tr>
                              <td>Measure Torque</td>
                              <td>Measures the torque applied to the steering wheel</td>
                              <td>-</td>
                              <td>Torque value in Nm</td>
                            </tr>
                            <tr>
                              <td>Calculate Steer Angle</td>
                              <td>Converts the measured torque into the corresponding steer angle</td>
                              <td>Torque value in Nm</td>
                              <td>Steer angle in degrees</td>
                            </tr>
                            <tr>
                              <td>Provide Feedback</td>
                              <td>Provides feedback to the vehicle's electronic control system</td>
                              <td>Steer angle in degrees</td>
                              <td>-</td>
                            </tr>
                          </table>
                        </body>
                        </html>
                        ```

                        You can save this code as an HTML file and open it in a web browser to view the table.
                        */ 
                        @CapellaID { eid = "16a3536d-10f0-4e26-8310-756d28011025"; } 
                        attribute :>> isAbstract = false; 
                        attribute :>> isActor = false; 
                        attribute :>> isHuman = false; 
                        attribute :>> kind = PhysicalComponentKind::HARDWARE; 
                        attribute :>> nature = PhysicalComponentNature::BEHAVIOR; 
                        allocation '8235c52e-55b8-437e-bd42-be82d6f34b16' : ComponentFunctionalAllocation
                            allocate function ::> 'eRod_Autonomous_Vehicle_2024 Project'::'eRod_Autonomous_Vehicle_2024'::'Physical Architecture'::'Physical Functions'::'Root Physical Function'.'Steer Wheels'.'Measure steering force'
                            to component ::> 'eRod_Autonomous_Vehicle_2024 Project'::'eRod_Autonomous_Vehicle_2024'::'Physical Architecture'::'Structure'::'Physical System'.'Steer Torque Sensor';
                        perform 'eRod_Autonomous_Vehicle_2024 Project'::'eRod_Autonomous_Vehicle_2024'::'Physical Architecture'::'Physical Functions'::'Root Physical Function'.'Steer Wheels'.'Measure steering force' ; 
                        allocation '0a03c6b2-3ddd-4349-ac79-8e1834026f1d' : ComponentFunctionalAllocation
                            allocate function ::> 'eRod_Autonomous_Vehicle_2024 Project'::'eRod_Autonomous_Vehicle_2024'::'Physical Architecture'::'Physical Functions'::'Root Physical Function'.'Steer Wheels'.'Measure steering angle'
                            to component ::> 'eRod_Autonomous_Vehicle_2024 Project'::'eRod_Autonomous_Vehicle_2024'::'Physical Architecture'::'Structure'::'Physical System'.'Steer Torque Sensor';
                        perform 'eRod_Autonomous_Vehicle_2024 Project'::'eRod_Autonomous_Vehicle_2024'::'Physical Architecture'::'Physical Functions'::'Root Physical Function'.'Steer Wheels'.'Measure steering angle' ; 
                        port 'CP 1' : ComponentPort { 
                            @CapellaID { eid = "54a07e10-f2e8-4c78-8901-0a2a9d952c16"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                            ref allocation 'eac307be-a505-44af-af22-edbb04ffbfb6' : PortAllocation
                                allocate allocatedPort ::> 'eRod_Autonomous_Vehicle_2024 Project'::'eRod_Autonomous_Vehicle_2024'::'Physical Architecture'::'Physical Functions'::'Root Physical Function'.'Steer Wheels'.'Measure steering force'.'FOP 1'
                                to allocatingPort ::> 'eRod_Autonomous_Vehicle_2024 Project'::'eRod_Autonomous_Vehicle_2024'::'Physical Architecture'::'Structure'::'Physical System'.'Steer Torque Sensor'.'CP 1'; 
                            ref allocation 'a60e7ac8-69c5-4e88-b32c-8fdcdc40b592' : PortAllocation
                                allocate allocatedPort ::> 'eRod_Autonomous_Vehicle_2024 Project'::'eRod_Autonomous_Vehicle_2024'::'Physical Architecture'::'Physical Functions'::'Root Physical Function'.'Steer Wheels'.'Measure steering angle'.'FOP 1'
                                to allocatingPort ::> 'eRod_Autonomous_Vehicle_2024 Project'::'eRod_Autonomous_Vehicle_2024'::'Physical Architecture'::'Structure'::'Physical System'.'Steer Torque Sensor'.'CP 1'; 
                            ref :>> requiredInterfaces =  ('eRod_Autonomous_Vehicle_2024 Project'::'eRod_Autonomous_Vehicle_2024'::'Physical Architecture'::'Interfaces'::'Steering'); 
                            ref :>> ownedPortAllocations =  ('eRod_Autonomous_Vehicle_2024 Project'::'eRod_Autonomous_Vehicle_2024'::'Physical Architecture'::'Structure'::'Physical System'.'Steer Torque Sensor'.'CP 1'.'eac307be-a505-44af-af22-edbb04ffbfb6',
                            'eRod_Autonomous_Vehicle_2024 Project'::'eRod_Autonomous_Vehicle_2024'::'Physical Architecture'::'Structure'::'Physical System'.'Steer Torque Sensor'.'CP 1'.'a60e7ac8-69c5-4e88-b32c-8fdcdc40b592'); 
                        }  
                        port 'CP 4' : ComponentPort { 
                            @CapellaID { eid = "df5f0502-ae0a-4997-bad2-75134f27fed2"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                            ref allocation '88c63e4d-e34e-42b3-9a29-63ce406f2ad8' : PortAllocation
                                allocate allocatedPort ::> 'eRod_Autonomous_Vehicle_2024 Project'::'eRod_Autonomous_Vehicle_2024'::'Physical Architecture'::'Physical Functions'::'Root Physical Function'.'Steer Wheels'.'Measure steering angle'.'FIP 1'
                                to allocatingPort ::> 'eRod_Autonomous_Vehicle_2024 Project'::'eRod_Autonomous_Vehicle_2024'::'Physical Architecture'::'Structure'::'Physical System'.'Steer Torque Sensor'.'CP 4'; 
                            ref allocation 'd95fcb85-19e0-4d83-bd85-9765b04ea96a' : PortAllocation
                                allocate allocatedPort ::> 'eRod_Autonomous_Vehicle_2024 Project'::'eRod_Autonomous_Vehicle_2024'::'Physical Architecture'::'Physical Functions'::'Root Physical Function'.'Steer Wheels'.'Measure steering force'.'FIP 1'
                                to allocatingPort ::> 'eRod_Autonomous_Vehicle_2024 Project'::'eRod_Autonomous_Vehicle_2024'::'Physical Architecture'::'Structure'::'Physical System'.'Steer Torque Sensor'.'CP 4'; 
                            ref :>> ownedPortAllocations =  ('eRod_Autonomous_Vehicle_2024 Project'::'eRod_Autonomous_Vehicle_2024'::'Physical Architecture'::'Structure'::'Physical System'.'Steer Torque Sensor'.'CP 4'.'88c63e4d-e34e-42b3-9a29-63ce406f2ad8',
                            'eRod_Autonomous_Vehicle_2024 Project'::'eRod_Autonomous_Vehicle_2024'::'Physical Architecture'::'Structure'::'Physical System'.'Steer Torque Sensor'.'CP 4'.'d95fcb85-19e0-4d83-bd85-9765b04ea96a'); 
                            ref :>> providedInterfaces =  ('eRod_Autonomous_Vehicle_2024 Project'::'eRod_Autonomous_Vehicle_2024'::'Physical Architecture'::'Interfaces'::'Steer Torque Interface'); 
                        }  
                        state 'StateMachine 1' : StateMachine  { 
                            @CapellaID { eid = "4933597b-0f46-4e74-be4f-1f4423dfa893"; } 
                            attribute :>> isControlOperator = false; 
                            state 'State 2' : State  { 
                                @CapellaID { eid = "fd9d4a7b-6f47-4868-9b92-a7a05d79715c"; } 
                            }  
                            state 'State 3' : State  { 
                                @CapellaID { eid = "aa23b652-26fc-4c58-8361-a08f21f05859"; } 
                            }  
                            entry; then 'State 2';  
                            transition '1bd47615-bbd1-436c-96d3-5dbee1287704' 
                                first 'eRod_Autonomous_Vehicle_2024 Project'::'eRod_Autonomous_Vehicle_2024'::'Physical Architecture'::'Structure'::'Physical System'.'Steer Torque Sensor'.'StateMachine 1'.'State 2'
                                do 'eRod_Autonomous_Vehicle_2024 Project'::'eRod_Autonomous_Vehicle_2024'::'Physical Architecture'::'Physical Functions'::'Root Physical Function'.'Steer Wheels'.'Measure steering force'
                                then 'eRod_Autonomous_Vehicle_2024 Project'::'eRod_Autonomous_Vehicle_2024'::'Physical Architecture'::'Structure'::'Physical System'.'Steer Torque Sensor'.'StateMachine 1'.'State 3' {
                            }  
                        }  
                        ref :>> ownedFunctionalAllocation =  ('eRod_Autonomous_Vehicle_2024 Project'::'eRod_Autonomous_Vehicle_2024'::'Physical Architecture'::'Structure'::'Physical System'.'Steer Torque Sensor'.'8235c52e-55b8-437e-bd42-be82d6f34b16',
                        'eRod_Autonomous_Vehicle_2024 Project'::'eRod_Autonomous_Vehicle_2024'::'Physical Architecture'::'Structure'::'Physical System'.'Steer Torque Sensor'.'0a03c6b2-3ddd-4349-ac79-8e1834026f1d'); 
                        ref :>> ownedStateMachines =  ('eRod_Autonomous_Vehicle_2024 Project'::'eRod_Autonomous_Vehicle_2024'::'Physical Architecture'::'Structure'::'Physical System'.'Steer Torque Sensor'.'StateMachine 1'); 
                    }  
                    part 'EPS Controller' : PhysicalComponent { 
                        @CapellaID { eid = "3df0a939-f14c-463f-a7d6-73709bc4455d"; } 
                        attribute :>> isAbstract = false; 
                        attribute :>> isActor = false; 
                        attribute :>> isHuman = false; 
                        attribute :>> kind = PhysicalComponentKind::UNSET; 
                        attribute :>> nature = PhysicalComponentNature::BEHAVIOR; 
                        allocation 'b6e507bb-8124-4e16-ba4f-470f66ce2ee7' : ComponentFunctionalAllocation
                            allocate function ::> 'eRod_Autonomous_Vehicle_2024 Project'::'eRod_Autonomous_Vehicle_2024'::'Physical Architecture'::'Physical Functions'::'Root Physical Function'.'Pull drift compensation (PDC)'
                            to component ::> 'eRod_Autonomous_Vehicle_2024 Project'::'eRod_Autonomous_Vehicle_2024'::'Physical Architecture'::'Structure'::'Physical System'.'EPS Controller';
                        perform 'eRod_Autonomous_Vehicle_2024 Project'::'eRod_Autonomous_Vehicle_2024'::'Physical Architecture'::'Physical Functions'::'Root Physical Function'.'Pull drift compensation (PDC)' ; 
                        allocation '2b7a4a1e-1c5d-4869-89fb-6df8c860adb4' : ComponentFunctionalAllocation
                            allocate function ::> 'eRod_Autonomous_Vehicle_2024 Project'::'eRod_Autonomous_Vehicle_2024'::'Physical Architecture'::'Physical Functions'::'Root Physical Function'.'Steer Wheels'.'Torque steer compensation (TSC)'
                            to component ::> 'eRod_Autonomous_Vehicle_2024 Project'::'eRod_Autonomous_Vehicle_2024'::'Physical Architecture'::'Structure'::'Physical System'.'EPS Controller';
                        perform 'eRod_Autonomous_Vehicle_2024 Project'::'eRod_Autonomous_Vehicle_2024'::'Physical Architecture'::'Physical Functions'::'Root Physical Function'.'Steer Wheels'.'Torque steer compensation (TSC)' ; 
                        allocation '67f6e96a-7791-40ce-aa0a-b28feb0f95e2' : ComponentFunctionalAllocation
                            allocate function ::> 'eRod_Autonomous_Vehicle_2024 Project'::'eRod_Autonomous_Vehicle_2024'::'Physical Architecture'::'Physical Functions'::'Root Physical Function'.'Active nibble compensation (ANC)'
                            to component ::> 'eRod_Autonomous_Vehicle_2024 Project'::'eRod_Autonomous_Vehicle_2024'::'Physical Architecture'::'Structure'::'Physical System'.'EPS Controller';
                        perform 'eRod_Autonomous_Vehicle_2024 Project'::'eRod_Autonomous_Vehicle_2024'::'Physical Architecture'::'Physical Functions'::'Root Physical Function'.'Active nibble compensation (ANC)' ; 
                        allocation '55f98fe6-83a0-4798-bdce-3f2a96148af2' : ComponentFunctionalAllocation
                            allocate function ::> 'eRod_Autonomous_Vehicle_2024 Project'::'eRod_Autonomous_Vehicle_2024'::'Physical Architecture'::'Physical Functions'::'Root Physical Function'.'Arbiter/limiter (A/L)'
                            to component ::> 'eRod_Autonomous_Vehicle_2024 Project'::'eRod_Autonomous_Vehicle_2024'::'Physical Architecture'::'Structure'::'Physical System'.'EPS Controller';
                        perform 'eRod_Autonomous_Vehicle_2024 Project'::'eRod_Autonomous_Vehicle_2024'::'Physical Architecture'::'Physical Functions'::'Root Physical Function'.'Arbiter/limiter (A/L)' ; 
                        allocation '3a9ae5fe-52b8-464b-91c4-15256f1b898e' : ComponentFunctionalAllocation
                            allocate function ::> 'eRod_Autonomous_Vehicle_2024 Project'::'eRod_Autonomous_Vehicle_2024'::'Physical Architecture'::'Physical Functions'::'Root Physical Function'.'Steer Feel (SF)'
                            to component ::> 'eRod_Autonomous_Vehicle_2024 Project'::'eRod_Autonomous_Vehicle_2024'::'Physical Architecture'::'Structure'::'Physical System'.'EPS Controller';
                        perform 'eRod_Autonomous_Vehicle_2024 Project'::'eRod_Autonomous_Vehicle_2024'::'Physical Architecture'::'Physical Functions'::'Root Physical Function'.'Steer Feel (SF)' ; 
                        port 'CP 1' : ComponentPort { 
                            @CapellaID { eid = "3bc4ede2-e6ae-4a4a-9c78-185ca5aaf4c9"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                        }  
                        port 'CP 3' : ComponentPort { 
                            @CapellaID { eid = "24054961-eff8-4cfe-8089-8628fca9fd64"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                            ref allocation '094d641e-0081-4538-b2c9-41b72fc8bae9' : PortAllocation
                                allocate allocatedPort ::> 'eRod_Autonomous_Vehicle_2024 Project'::'eRod_Autonomous_Vehicle_2024'::'Physical Architecture'::'Physical Functions'::'Root Physical Function'.'Steer Wheels'.'Torque steer compensation (TSC)'.'FIP 1'
                                to allocatingPort ::> 'eRod_Autonomous_Vehicle_2024 Project'::'eRod_Autonomous_Vehicle_2024'::'Physical Architecture'::'Structure'::'Physical System'.'EPS Controller'.'CP 3'; 
                            ref allocation 'e423a79d-3249-4d13-a76b-20a87a74e712' : PortAllocation
                                allocate allocatedPort ::> 'eRod_Autonomous_Vehicle_2024 Project'::'eRod_Autonomous_Vehicle_2024'::'Physical Architecture'::'Physical Functions'::'Root Physical Function'.'Steer Wheels'.'Torque steer compensation (TSC)'.'FIP 3'
                                to allocatingPort ::> 'eRod_Autonomous_Vehicle_2024 Project'::'eRod_Autonomous_Vehicle_2024'::'Physical Architecture'::'Structure'::'Physical System'.'EPS Controller'.'CP 3'; 
                            ref :>> ownedPortAllocations =  ('eRod_Autonomous_Vehicle_2024 Project'::'eRod_Autonomous_Vehicle_2024'::'Physical Architecture'::'Structure'::'Physical System'.'EPS Controller'.'CP 3'.'094d641e-0081-4538-b2c9-41b72fc8bae9',
                            'eRod_Autonomous_Vehicle_2024 Project'::'eRod_Autonomous_Vehicle_2024'::'Physical Architecture'::'Structure'::'Physical System'.'EPS Controller'.'CP 3'.'e423a79d-3249-4d13-a76b-20a87a74e712'); 
                            ref :>> providedInterfaces =  ('eRod_Autonomous_Vehicle_2024 Project'::'eRod_Autonomous_Vehicle_2024'::'Physical Architecture'::'Interfaces'::'Steering'); 
                        }  
                        port 'CP 4' : ComponentPort { 
                            @CapellaID { eid = "0a59ed5a-4f9d-4db6-b43b-644878dfe428"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                            ref allocation '034065bb-9dd1-4718-bfb1-38f73adcbaa1' : PortAllocation
                                allocate allocatedPort ::> 'eRod_Autonomous_Vehicle_2024 Project'::'eRod_Autonomous_Vehicle_2024'::'Physical Architecture'::'Physical Functions'::'Root Physical Function'.'Steer Wheels'.'Torque steer compensation (TSC)'.'FOP 1'
                                to allocatingPort ::> 'eRod_Autonomous_Vehicle_2024 Project'::'eRod_Autonomous_Vehicle_2024'::'Physical Architecture'::'Structure'::'Physical System'.'EPS Controller'.'CP 4'; 
                            ref :>> ownedPortAllocations =  ('eRod_Autonomous_Vehicle_2024 Project'::'eRod_Autonomous_Vehicle_2024'::'Physical Architecture'::'Structure'::'Physical System'.'EPS Controller'.'CP 4'.'034065bb-9dd1-4718-bfb1-38f73adcbaa1'); 
                        }  
                        port 'CP 5' : ComponentPort { 
                            @CapellaID { eid = "3f4d834c-4ea9-464d-a4da-d3205b4692f1"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                        }  
                        ref :>> ownedFunctionalAllocation =  ('eRod_Autonomous_Vehicle_2024 Project'::'eRod_Autonomous_Vehicle_2024'::'Physical Architecture'::'Structure'::'Physical System'.'EPS Controller'.'b6e507bb-8124-4e16-ba4f-470f66ce2ee7',
                        'eRod_Autonomous_Vehicle_2024 Project'::'eRod_Autonomous_Vehicle_2024'::'Physical Architecture'::'Structure'::'Physical System'.'EPS Controller'.'2b7a4a1e-1c5d-4869-89fb-6df8c860adb4',
                        'eRod_Autonomous_Vehicle_2024 Project'::'eRod_Autonomous_Vehicle_2024'::'Physical Architecture'::'Structure'::'Physical System'.'EPS Controller'.'67f6e96a-7791-40ce-aa0a-b28feb0f95e2',
                        'eRod_Autonomous_Vehicle_2024 Project'::'eRod_Autonomous_Vehicle_2024'::'Physical Architecture'::'Structure'::'Physical System'.'EPS Controller'.'55f98fe6-83a0-4798-bdce-3f2a96148af2',
                        'eRod_Autonomous_Vehicle_2024 Project'::'eRod_Autonomous_Vehicle_2024'::'Physical Architecture'::'Structure'::'Physical System'.'EPS Controller'.'3a9ae5fe-52b8-464b-91c4-15256f1b898e'); 
                    }  
                    part 'Motor Controller' : PhysicalComponent { 
                        doc /*
                        Sure! Here's an example of a formal HTML table for a Motor Controller:

                        ```html
                        <!DOCTYPE html>
                        <html>
                        <head>
                          <style>
                            table {
                              border-collapse: collapse;
                              width: 100%;
                            }
                            
                            th, td {
                              text-align: left;
                              padding: 8px;
                            }
                            
                            tr:nth-child(even) {
                              background-color: #f2f2f2;
                            }
                            
                            th {
                              background-color: #4CAF50;
                              color: white;
                            }
                          </style>
                        </head>
                        <body>

                        <h2>Motor Controller Functions</h2>

                        <table>
                          <tr>
                            <th>Function</th>
                            <th>Summary</th>
                            <th>Inputs</th>
                            <th>Outputs</th>
                          </tr>
                          <tr>
                            <td>Start</td>
                            <td>Starts the motor</td>
                            <td>No inputs required</td>
                            <td>No outputs produced</td>
                          </tr>
                          <tr>
                            <td>Stop</td>
                            <td>Stops the motor</td>
                            <td>No inputs required</td>
                            <td>No outputs produced</td>
                          </tr>
                          <tr>
                            <td>Speed Up</td>
                            <td>Increases the speed of the motor</td>
                            <td>No inputs required</td>
                            <td>No outputs produced</td>
                          </tr>
                          <tr>
                            <td>Slow Down</td>
                            <td>Decreases the speed of the motor</td>
                            <td>No inputs required</td>
                            <td>No outputs produced</td>
                          </tr>
                        </table>

                        </body>
                        </html>
                        ```

                        You can customize the table's style by editing the CSS inside the `<style>` tags.
                        */ 
                        @CapellaID { eid = "dec88348-47d2-4083-a673-985fabe190ad"; } 
                        attribute :>> isAbstract = false; 
                        attribute :>> isActor = false; 
                        attribute :>> isHuman = false; 
                        attribute :>> kind = PhysicalComponentKind::HARDWARE; 
                        attribute :>> nature = PhysicalComponentNature::BEHAVIOR; 
                        allocation '0947a1a4-0488-4aba-b3a9-0a695974358a' : ComponentFunctionalAllocation
                            allocate function ::> 'eRod_Autonomous_Vehicle_2024 Project'::'eRod_Autonomous_Vehicle_2024'::'Physical Architecture'::'Physical Functions'::'Root Physical Function'.'Steer Wheels'.'Assist steering'
                            to component ::> 'eRod_Autonomous_Vehicle_2024 Project'::'eRod_Autonomous_Vehicle_2024'::'Physical Architecture'::'Structure'::'Physical System'.'Motor Controller';
                        perform 'eRod_Autonomous_Vehicle_2024 Project'::'eRod_Autonomous_Vehicle_2024'::'Physical Architecture'::'Physical Functions'::'Root Physical Function'.'Steer Wheels'.'Assist steering' ; 
                        port 'CP 1' : ComponentPort { 
                            @CapellaID { eid = "a132c4ce-35ac-4d4c-a60c-9038963f8cf1"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                            ref allocation '3f611cb6-7035-444a-9006-ee0f630fcd9d' : PortAllocation
                                allocate allocatedPort ::> 'eRod_Autonomous_Vehicle_2024 Project'::'eRod_Autonomous_Vehicle_2024'::'Physical Architecture'::'Physical Functions'::'Root Physical Function'.'Steer Wheels'.'Assist steering'.'FIP 1'
                                to allocatingPort ::> 'eRod_Autonomous_Vehicle_2024 Project'::'eRod_Autonomous_Vehicle_2024'::'Physical Architecture'::'Structure'::'Physical System'.'Motor Controller'.'CP 1'; 
                            ref :>> ownedPortAllocations =  ('eRod_Autonomous_Vehicle_2024 Project'::'eRod_Autonomous_Vehicle_2024'::'Physical Architecture'::'Structure'::'Physical System'.'Motor Controller'.'CP 1'.'3f611cb6-7035-444a-9006-ee0f630fcd9d'); 
                        }  
                        port 'CP 2' : ComponentPort { 
                            @CapellaID { eid = "13e9d22e-4b44-4597-ae38-091f1d3d9a9f"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                            ref allocation '4b478919-95d2-4f1d-9e09-f8fcc4198ae6' : PortAllocation
                                allocate allocatedPort ::> 'eRod_Autonomous_Vehicle_2024 Project'::'eRod_Autonomous_Vehicle_2024'::'Physical Architecture'::'Physical Functions'::'Root Physical Function'.'Steer Wheels'.'Assist steering'.'FOP 2'
                                to allocatingPort ::> 'eRod_Autonomous_Vehicle_2024 Project'::'eRod_Autonomous_Vehicle_2024'::'Physical Architecture'::'Structure'::'Physical System'.'Motor Controller'.'CP 2'; 
                            ref :>> ownedPortAllocations =  ('eRod_Autonomous_Vehicle_2024 Project'::'eRod_Autonomous_Vehicle_2024'::'Physical Architecture'::'Structure'::'Physical System'.'Motor Controller'.'CP 2'.'4b478919-95d2-4f1d-9e09-f8fcc4198ae6'); 
                        }  
                        port 'CP 3' : ComponentPort { 
                            @CapellaID { eid = "0917926b-1b26-4351-952b-de5405490ebf"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                            ref allocation 'db8941eb-7cb5-43b0-85ac-85132d9a734a' : PortAllocation
                                allocate allocatedPort ::> 'eRod_Autonomous_Vehicle_2024 Project'::'eRod_Autonomous_Vehicle_2024'::'Physical Architecture'::'Physical Functions'::'Root Physical Function'.'Steer Wheels'.'Assist steering'.'FOP 4'
                                to allocatingPort ::> 'eRod_Autonomous_Vehicle_2024 Project'::'eRod_Autonomous_Vehicle_2024'::'Physical Architecture'::'Structure'::'Physical System'.'Motor Controller'.'CP 3'; 
                            ref :>> ownedPortAllocations =  ('eRod_Autonomous_Vehicle_2024 Project'::'eRod_Autonomous_Vehicle_2024'::'Physical Architecture'::'Structure'::'Physical System'.'Motor Controller'.'CP 3'.'db8941eb-7cb5-43b0-85ac-85132d9a734a'); 
                        }  
                        ref :>> ownedFunctionalAllocation =  ('eRod_Autonomous_Vehicle_2024 Project'::'eRod_Autonomous_Vehicle_2024'::'Physical Architecture'::'Structure'::'Physical System'.'Motor Controller'.'0947a1a4-0488-4aba-b3a9-0a695974358a'); 
                    }  
                    part 'AV Controller' : PhysicalComponent { 
                        @CapellaID { eid = "39f2b49e-0c83-4de6-a441-12bfa10d4e43"; } 
                        attribute :>> isAbstract = false; 
                        attribute :>> isActor = false; 
                        attribute :>> isHuman = false; 
                        attribute :>> kind = PhysicalComponentKind::HARDWARE; 
                        attribute :>> nature = PhysicalComponentNature::BEHAVIOR; 
                        allocation '07659b84-3342-4e63-acc5-409df42d97b0' : ComponentFunctionalAllocation
                            allocate function ::> 'eRod_Autonomous_Vehicle_2024 Project'::'eRod_Autonomous_Vehicle_2024'::'Physical Architecture'::'Physical Functions'::'Root Physical Function'.'Prevent accent'
                            to component ::> 'eRod_Autonomous_Vehicle_2024 Project'::'eRod_Autonomous_Vehicle_2024'::'Physical Architecture'::'Structure'::'Physical System'.'AV Controller';
                        perform 'eRod_Autonomous_Vehicle_2024 Project'::'eRod_Autonomous_Vehicle_2024'::'Physical Architecture'::'Physical Functions'::'Root Physical Function'.'Prevent accent' ; 
                        allocation 'd1ccf039-d2db-42e1-8d46-55554a17db9f' : ComponentFunctionalAllocation
                            allocate function ::> 'eRod_Autonomous_Vehicle_2024 Project'::'eRod_Autonomous_Vehicle_2024'::'Physical Architecture'::'Physical Functions'::'Root Physical Function'.'Steer Wheels'.'Automatic Steering'
                            to component ::> 'eRod_Autonomous_Vehicle_2024 Project'::'eRod_Autonomous_Vehicle_2024'::'Physical Architecture'::'Structure'::'Physical System'.'AV Controller';
                        perform 'eRod_Autonomous_Vehicle_2024 Project'::'eRod_Autonomous_Vehicle_2024'::'Physical Architecture'::'Physical Functions'::'Root Physical Function'.'Steer Wheels'.'Automatic Steering' ; 
                        allocation 'f2ffc907-32d5-4b64-8cd3-66cf697b01cb' : ComponentFunctionalAllocation
                            allocate function ::> 'eRod_Autonomous_Vehicle_2024 Project'::'eRod_Autonomous_Vehicle_2024'::'Physical Architecture'::'Physical Functions'::'Root Physical Function'.'Drive route'
                            to component ::> 'eRod_Autonomous_Vehicle_2024 Project'::'eRod_Autonomous_Vehicle_2024'::'Physical Architecture'::'Structure'::'Physical System'.'AV Controller';
                        perform 'eRod_Autonomous_Vehicle_2024 Project'::'eRod_Autonomous_Vehicle_2024'::'Physical Architecture'::'Physical Functions'::'Root Physical Function'.'Drive route' ; 
                        port 'CP 1' : ComponentPort { 
                            @CapellaID { eid = "b51cad9d-0abb-487c-8c08-fe29f29f4b3f"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                        }  
                        port 'CP 3' : ComponentPort { 
                            @CapellaID { eid = "0c5f9030-a605-46ef-b745-4fb0775af776"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                        }  
                        ref :>> ownedFunctionalAllocation =  ('eRod_Autonomous_Vehicle_2024 Project'::'eRod_Autonomous_Vehicle_2024'::'Physical Architecture'::'Structure'::'Physical System'.'AV Controller'.'07659b84-3342-4e63-acc5-409df42d97b0',
                        'eRod_Autonomous_Vehicle_2024 Project'::'eRod_Autonomous_Vehicle_2024'::'Physical Architecture'::'Structure'::'Physical System'.'AV Controller'.'d1ccf039-d2db-42e1-8d46-55554a17db9f',
                        'eRod_Autonomous_Vehicle_2024 Project'::'eRod_Autonomous_Vehicle_2024'::'Physical Architecture'::'Structure'::'Physical System'.'AV Controller'.'f2ffc907-32d5-4b64-8cd3-66cf697b01cb'); 
                         
                    }  
                    part 'Perception ' : PhysicalComponent { 
                        doc /*
                        Sure! Here is an example of a formal HTML table for a Perception:

                        ```html
                        <!DOCTYPE html>
                        <html>
                        <head>
                          <title>Perception Functions</title>
                          <style>
                            table {
                              border-collapse: collapse;
                              width: 100%;
                            }

                            th, td {
                              border: 1px solid black;
                              padding: 8px;
                              text-align: left;
                            }

                            th {
                              background-color: #f2f2f2;
                            }

                            tr:nth-child(even) {
                              background-color: #dddddd;
                            }
                          </style>
                        </head>
                        <body>
                          <h1>Perception Functions</h1>
                          <table>
                            <tr>
                              <th>Function</th>
                              <th>Summary</th>
                              <th>Inputs</th>
                              <th>Outputs</th>
                            </tr>
                            <tr>
                              <td>perceiveSound()</td>
                              <td>Perceives sound in the environment</td>
                              <td>Audio input</td>
                              <td>Interpreted sound information</td>
                            </tr>
                            <tr>
                              <td>perceiveVision()</td>
                              <td>Perceives visual information in the environment</td>
                              <td>Visual input</td>
                              <td>Analyzed visual data</td>
                            </tr>
                            <tr>
                              <td>perceiveTouch()</td>
                              <td>Perceives physical touch sensations</td>
                              <td>Tactile input</td>
                              <td>Haptic feedback or tactile information</td>
                            </tr>
                            <!-- Add more rows for additional perception functions -->
                          </table>
                        </body>
                        </html>
                        ```

                        You can add more rows for additional perception functions by duplicating the last `<tr>` section and modifying the content accordingly. Make sure to replace the comments with the respective function information.
                        */ 
                        @CapellaID { eid = "9a86536b-a343-4ff0-861b-e8616d79b72a"; } 
                        attribute :>> isAbstract = false; 
                        attribute :>> isActor = false; 
                        attribute :>> isHuman = false; 
                        attribute :>> kind = PhysicalComponentKind::UNSET; 
                        attribute :>> nature = PhysicalComponentNature::BEHAVIOR; 
                        allocation '7a9d1fda-142c-40f9-a200-558f29a09db7' : ComponentFunctionalAllocation
                            allocate function ::> 'eRod_Autonomous_Vehicle_2024 Project'::'eRod_Autonomous_Vehicle_2024'::'Physical Architecture'::'Physical Functions'::'Root Physical Function'.'Detect Objects'
                            to component ::> 'eRod_Autonomous_Vehicle_2024 Project'::'eRod_Autonomous_Vehicle_2024'::'Physical Architecture'::'Structure'::'Physical System'.'Perception ';
                        perform 'eRod_Autonomous_Vehicle_2024 Project'::'eRod_Autonomous_Vehicle_2024'::'Physical Architecture'::'Physical Functions'::'Root Physical Function'.'Detect Objects' ; 
                        ref :>> ownedFunctionalAllocation =  ('eRod_Autonomous_Vehicle_2024 Project'::'eRod_Autonomous_Vehicle_2024'::'Physical Architecture'::'Structure'::'Physical System'.'Perception '.'7a9d1fda-142c-40f9-a200-558f29a09db7'); 
                    }  
                    part 'Image Processing (Left Camera)' : PhysicalComponent { 
                        @CapellaID { eid = "7235203b-6a00-47b6-9d7f-a7e4e3756c32"; } 
                        attribute :>> isAbstract = false; 
                        attribute :>> isActor = false; 
                        attribute :>> isHuman = false; 
                        attribute :>> kind = PhysicalComponentKind::UNSET; 
                        attribute :>> nature = PhysicalComponentNature::BEHAVIOR; 
                    }  
                    part 'Image Processing (Right Camera)' : PhysicalComponent { 
                        @CapellaID { eid = "6ed86cd8-7156-46d3-9575-6186a335a2b5"; } 
                        attribute :>> isAbstract = false; 
                        attribute :>> isActor = false; 
                        attribute :>> isHuman = false; 
                        attribute :>> kind = PhysicalComponentKind::UNSET; 
                        attribute :>> nature = PhysicalComponentNature::BEHAVIOR; 
                    }  
                    part 'Image Processing (Front Camera)' : PhysicalComponent { 
                        @CapellaID { eid = "9b31b071-dfa4-4128-bf55-6cd7a93dd779"; } 
                        attribute :>> isAbstract = false; 
                        attribute :>> isActor = false; 
                        attribute :>> isHuman = false; 
                        attribute :>> kind = PhysicalComponentKind::UNSET; 
                        attribute :>> nature = PhysicalComponentNature::BEHAVIOR; 
                    }  
                    part 'Image Processing (Rear Camera)' : PhysicalComponent { 
                        @CapellaID { eid = "b8ce2d1b-b682-4a76-ae12-af634666e6e6"; } 
                        attribute :>> isAbstract = false; 
                        attribute :>> isActor = false; 
                        attribute :>> isHuman = false; 
                        attribute :>> kind = PhysicalComponentKind::UNSET; 
                        attribute :>> nature = PhysicalComponentNature::BEHAVIOR; 
                    }  
                    part 'Brake Controller' : PhysicalComponent { 
                        @CapellaID { eid = "a02e8a24-6973-4e86-bf5a-077bd575fb5b"; } 
                        attribute :>> isAbstract = false; 
                        attribute :>> isActor = false; 
                        attribute :>> isHuman = false; 
                        attribute :>> kind = PhysicalComponentKind::UNSET; 
                        attribute :>> nature = PhysicalComponentNature::BEHAVIOR; 
                        port 'CP 1' : ComponentPort { 
                            @CapellaID { eid = "c72efc16-51c2-41ae-9ead-dd2ff1eb335b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                        }  
                    }  
                    part 'Autonomous Vehicle (AV) System' : PhysicalComponent { 
                        @CapellaID { eid = "0738b350-f993-45b8-8b3e-d2bbcb1696ae"; } 
                        attribute :>> isAbstract = false; 
                        attribute :>> isActor = false; 
                        attribute :>> isHuman = false; 
                        attribute :>> kind = PhysicalComponentKind::UNSET; 
                        attribute :>> nature = PhysicalComponentNature::BEHAVIOR; 
                        part 'Perception' : PhysicalComponent { 
                            @CapellaID { eid = "c489011d-4b53-4a70-be03-e1f405d68928"; } 
                            attribute :>> isAbstract = false; 
                            attribute :>> isActor = false; 
                            attribute :>> isHuman = false; 
                            attribute :>> kind = PhysicalComponentKind::UNSET; 
                            attribute :>> nature = PhysicalComponentNature::BEHAVIOR; 
                            allocation '27e4a2a8-55fa-4d37-97c4-f14474f19a48' : ComponentFunctionalAllocation
                                allocate function ::> 'eRod_Autonomous_Vehicle_2024 Project'::'eRod_Autonomous_Vehicle_2024'::'Physical Architecture'::'Physical Functions'::'Root Physical Function'.'Detect obstacles'
                                to component ::> 'eRod_Autonomous_Vehicle_2024 Project'::'eRod_Autonomous_Vehicle_2024'::'Physical Architecture'::'Structure'::'Physical System'.'Autonomous Vehicle (AV) System'.'Perception';
                            perform 'eRod_Autonomous_Vehicle_2024 Project'::'eRod_Autonomous_Vehicle_2024'::'Physical Architecture'::'Physical Functions'::'Root Physical Function'.'Detect obstacles' ; 
                            allocation '5058e005-1270-4db8-ad18-0b277abf93df' : ComponentFunctionalAllocation
                                allocate function ::> 'eRod_Autonomous_Vehicle_2024 Project'::'eRod_Autonomous_Vehicle_2024'::'Physical Architecture'::'Physical Functions'::'Root Physical Function'.'Detect road'.'Detect path'
                                to component ::> 'eRod_Autonomous_Vehicle_2024 Project'::'eRod_Autonomous_Vehicle_2024'::'Physical Architecture'::'Structure'::'Physical System'.'Autonomous Vehicle (AV) System'.'Perception';
                            perform 'eRod_Autonomous_Vehicle_2024 Project'::'eRod_Autonomous_Vehicle_2024'::'Physical Architecture'::'Physical Functions'::'Root Physical Function'.'Detect road'.'Detect path' ; 
                            allocation 'eb8a6c27-c4a5-4187-aacc-ee48ac5e83da' : ComponentFunctionalAllocation
                                allocate function ::> 'eRod_Autonomous_Vehicle_2024 Project'::'eRod_Autonomous_Vehicle_2024'::'Physical Architecture'::'Physical Functions'::'Root Physical Function'.'Detect intersections'
                                to component ::> 'eRod_Autonomous_Vehicle_2024 Project'::'eRod_Autonomous_Vehicle_2024'::'Physical Architecture'::'Structure'::'Physical System'.'Autonomous Vehicle (AV) System'.'Perception';
                            perform 'eRod_Autonomous_Vehicle_2024 Project'::'eRod_Autonomous_Vehicle_2024'::'Physical Architecture'::'Physical Functions'::'Root Physical Function'.'Detect intersections' ; 
                            allocation 'd6f062f6-b723-4491-8a87-450d1aeb9121' : ComponentFunctionalAllocation
                                allocate function ::> 'eRod_Autonomous_Vehicle_2024 Project'::'eRod_Autonomous_Vehicle_2024'::'Physical Architecture'::'Physical Functions'::'Root Physical Function'.'Detect signs'
                                to component ::> 'eRod_Autonomous_Vehicle_2024 Project'::'eRod_Autonomous_Vehicle_2024'::'Physical Architecture'::'Structure'::'Physical System'.'Autonomous Vehicle (AV) System'.'Perception';
                            perform 'eRod_Autonomous_Vehicle_2024 Project'::'eRod_Autonomous_Vehicle_2024'::'Physical Architecture'::'Physical Functions'::'Root Physical Function'.'Detect signs' ; 
                            allocation '8ad6b8bf-b6b0-4f8b-8264-cb13fc7aaf07' : ComponentFunctionalAllocation
                                allocate function ::> 'eRod_Autonomous_Vehicle_2024 Project'::'eRod_Autonomous_Vehicle_2024'::'Physical Architecture'::'Physical Functions'::'Root Physical Function'.'Detect lights'
                                to component ::> 'eRod_Autonomous_Vehicle_2024 Project'::'eRod_Autonomous_Vehicle_2024'::'Physical Architecture'::'Structure'::'Physical System'.'Autonomous Vehicle (AV) System'.'Perception';
                            perform 'eRod_Autonomous_Vehicle_2024 Project'::'eRod_Autonomous_Vehicle_2024'::'Physical Architecture'::'Physical Functions'::'Root Physical Function'.'Detect lights' ; 
                            allocation '7d2b36cd-756d-48b2-b26d-530576fe5e38' : ComponentFunctionalAllocation
                                allocate function ::> 'eRod_Autonomous_Vehicle_2024 Project'::'eRod_Autonomous_Vehicle_2024'::'Physical Architecture'::'Physical Functions'::'Root Physical Function'.'Detect road'.'Image fusion'
                                to component ::> 'eRod_Autonomous_Vehicle_2024 Project'::'eRod_Autonomous_Vehicle_2024'::'Physical Architecture'::'Structure'::'Physical System'.'Autonomous Vehicle (AV) System'.'Perception';
                            perform 'eRod_Autonomous_Vehicle_2024 Project'::'eRod_Autonomous_Vehicle_2024'::'Physical Architecture'::'Physical Functions'::'Root Physical Function'.'Detect road'.'Image fusion' ; 
                            ref :>> ownedFunctionalAllocation =  ('eRod_Autonomous_Vehicle_2024 Project'::'eRod_Autonomous_Vehicle_2024'::'Physical Architecture'::'Structure'::'Physical System'.'Autonomous Vehicle (AV) System'.'Perception'.'27e4a2a8-55fa-4d37-97c4-f14474f19a48',
                            'eRod_Autonomous_Vehicle_2024 Project'::'eRod_Autonomous_Vehicle_2024'::'Physical Architecture'::'Structure'::'Physical System'.'Autonomous Vehicle (AV) System'.'Perception'.'5058e005-1270-4db8-ad18-0b277abf93df',
                            'eRod_Autonomous_Vehicle_2024 Project'::'eRod_Autonomous_Vehicle_2024'::'Physical Architecture'::'Structure'::'Physical System'.'Autonomous Vehicle (AV) System'.'Perception'.'eb8a6c27-c4a5-4187-aacc-ee48ac5e83da',
                            'eRod_Autonomous_Vehicle_2024 Project'::'eRod_Autonomous_Vehicle_2024'::'Physical Architecture'::'Structure'::'Physical System'.'Autonomous Vehicle (AV) System'.'Perception'.'d6f062f6-b723-4491-8a87-450d1aeb9121',
                            'eRod_Autonomous_Vehicle_2024 Project'::'eRod_Autonomous_Vehicle_2024'::'Physical Architecture'::'Structure'::'Physical System'.'Autonomous Vehicle (AV) System'.'Perception'.'8ad6b8bf-b6b0-4f8b-8264-cb13fc7aaf07',
                            'eRod_Autonomous_Vehicle_2024 Project'::'eRod_Autonomous_Vehicle_2024'::'Physical Architecture'::'Structure'::'Physical System'.'Autonomous Vehicle (AV) System'.'Perception'.'7d2b36cd-756d-48b2-b26d-530576fe5e38'); 
                             
                             
                        }  
                        part 'Mapping' : PhysicalComponent { 
                            @CapellaID { eid = "039efe86-940a-40b3-9473-7854c7bbeff5"; } 
                            attribute :>> isAbstract = false; 
                            attribute :>> isActor = false; 
                            attribute :>> isHuman = false; 
                            attribute :>> kind = PhysicalComponentKind::UNSET; 
                            attribute :>> nature = PhysicalComponentNature::BEHAVIOR; 
                            allocation 'efbe85db-5dab-46bb-89a6-db18378324e0' : ComponentFunctionalAllocation
                                allocate function ::> 'eRod_Autonomous_Vehicle_2024 Project'::'eRod_Autonomous_Vehicle_2024'::'Physical Architecture'::'Physical Functions'::'Root Physical Function'.'Plan path'
                                to component ::> 'eRod_Autonomous_Vehicle_2024 Project'::'eRod_Autonomous_Vehicle_2024'::'Physical Architecture'::'Structure'::'Physical System'.'Autonomous Vehicle (AV) System'.'Mapping';
                            perform 'eRod_Autonomous_Vehicle_2024 Project'::'eRod_Autonomous_Vehicle_2024'::'Physical Architecture'::'Physical Functions'::'Root Physical Function'.'Plan path' ; 
                            ref :>> ownedFunctionalAllocation =  ('eRod_Autonomous_Vehicle_2024 Project'::'eRod_Autonomous_Vehicle_2024'::'Physical Architecture'::'Structure'::'Physical System'.'Autonomous Vehicle (AV) System'.'Mapping'.'efbe85db-5dab-46bb-89a6-db18378324e0'); 
                             
                             
                        }  
                        part 'Drive' : PhysicalComponent { 
                            @CapellaID { eid = "40e3f5da-e5cb-4a63-beac-60988b79bfc4"; } 
                            attribute :>> isAbstract = false; 
                            attribute :>> isActor = false; 
                            attribute :>> isHuman = false; 
                            attribute :>> kind = PhysicalComponentKind::UNSET; 
                            attribute :>> nature = PhysicalComponentNature::BEHAVIOR; 
                             
                             
                        }  
                        ref :>> ownedPhysicalComponents =  ('eRod_Autonomous_Vehicle_2024 Project'::'eRod_Autonomous_Vehicle_2024'::'Physical Architecture'::'Structure'::'Physical System'.'Autonomous Vehicle (AV) System'.'Perception',
                        'eRod_Autonomous_Vehicle_2024 Project'::'eRod_Autonomous_Vehicle_2024'::'Physical Architecture'::'Structure'::'Physical System'.'Autonomous Vehicle (AV) System'.'Mapping',
                        'eRod_Autonomous_Vehicle_2024 Project'::'eRod_Autonomous_Vehicle_2024'::'Physical Architecture'::'Structure'::'Physical System'.'Autonomous Vehicle (AV) System'.'Drive'); 
                         
                         
                    }  
                    part 'Sensors' : PhysicalComponent { 
                        @CapellaID { eid = "f2438b8b-6ef8-44ec-8e4c-956e997beea9"; } 
                        attribute :>> isAbstract = false; 
                        attribute :>> isActor = false; 
                        attribute :>> isHuman = false; 
                        attribute :>> kind = PhysicalComponentKind::UNSET; 
                        attribute :>> nature = PhysicalComponentNature::BEHAVIOR; 
                        part 'Camera' : PhysicalComponent { 
                            @CapellaID { eid = "b4f342a0-c78b-4848-b6e4-16cf9476194b"; } 
                            attribute :>> isAbstract = false; 
                            attribute :>> isActor = false; 
                            attribute :>> isHuman = false; 
                            attribute :>> kind = PhysicalComponentKind::UNSET; 
                            attribute :>> nature = PhysicalComponentNature::BEHAVIOR; 
                            allocation '70b7af5c-02bd-4e56-b8df-f676a5c42d8d' : ComponentFunctionalAllocation
                                allocate function ::> 'eRod_Autonomous_Vehicle_2024 Project'::'eRod_Autonomous_Vehicle_2024'::'Physical Architecture'::'Physical Functions'::'Root Physical Function'.'Detect road'.'Capture view'
                                to component ::> 'eRod_Autonomous_Vehicle_2024 Project'::'eRod_Autonomous_Vehicle_2024'::'Physical Architecture'::'Structure'::'Physical System'.'Sensors'.'Camera';
                            perform 'eRod_Autonomous_Vehicle_2024 Project'::'eRod_Autonomous_Vehicle_2024'::'Physical Architecture'::'Physical Functions'::'Root Physical Function'.'Detect road'.'Capture view' ; 
                            ref :>> ownedFunctionalAllocation =  ('eRod_Autonomous_Vehicle_2024 Project'::'eRod_Autonomous_Vehicle_2024'::'Physical Architecture'::'Structure'::'Physical System'.'Sensors'.'Camera'.'70b7af5c-02bd-4e56-b8df-f676a5c42d8d'); 
                             
                             
                        }  
                        part 'Lidar' : PhysicalComponent { 
                            @CapellaID { eid = "50a06cc9-5ca2-4930-911a-63c54fb16952"; } 
                            attribute :>> isAbstract = false; 
                            attribute :>> isActor = false; 
                            attribute :>> isHuman = false; 
                            attribute :>> kind = PhysicalComponentKind::UNSET; 
                            attribute :>> nature = PhysicalComponentNature::BEHAVIOR; 
                            allocation '9c01cdb5-1ded-4ae6-bf4b-f295f4813301' : ComponentFunctionalAllocation
                                allocate function ::> 'eRod_Autonomous_Vehicle_2024 Project'::'eRod_Autonomous_Vehicle_2024'::'Physical Architecture'::'Physical Functions'::'Root Physical Function'.'Capture points'
                                to component ::> 'eRod_Autonomous_Vehicle_2024 Project'::'eRod_Autonomous_Vehicle_2024'::'Physical Architecture'::'Structure'::'Physical System'.'Sensors'.'Lidar';
                            perform 'eRod_Autonomous_Vehicle_2024 Project'::'eRod_Autonomous_Vehicle_2024'::'Physical Architecture'::'Physical Functions'::'Root Physical Function'.'Capture points' ; 
                            ref :>> ownedFunctionalAllocation =  ('eRod_Autonomous_Vehicle_2024 Project'::'eRod_Autonomous_Vehicle_2024'::'Physical Architecture'::'Structure'::'Physical System'.'Sensors'.'Lidar'.'9c01cdb5-1ded-4ae6-bf4b-f295f4813301'); 
                             
                             
                        }  
                        part 'Radar' : PhysicalComponent { 
                            @CapellaID { eid = "16ebd043-3191-46cd-84e0-92ee92630740"; } 
                            attribute :>> isAbstract = false; 
                            attribute :>> isActor = false; 
                            attribute :>> isHuman = false; 
                            attribute :>> kind = PhysicalComponentKind::UNSET; 
                            attribute :>> nature = PhysicalComponentNature::BEHAVIOR; 
                            allocation '68ec0773-d007-4df9-a136-9b6a2be6f8f9' : ComponentFunctionalAllocation
                                allocate function ::> 'eRod_Autonomous_Vehicle_2024 Project'::'eRod_Autonomous_Vehicle_2024'::'Physical Architecture'::'Physical Functions'::'Root Physical Function'.'Capture radar echo'
                                to component ::> 'eRod_Autonomous_Vehicle_2024 Project'::'eRod_Autonomous_Vehicle_2024'::'Physical Architecture'::'Structure'::'Physical System'.'Sensors'.'Radar';
                            perform 'eRod_Autonomous_Vehicle_2024 Project'::'eRod_Autonomous_Vehicle_2024'::'Physical Architecture'::'Physical Functions'::'Root Physical Function'.'Capture radar echo' ; 
                            ref :>> ownedFunctionalAllocation =  ('eRod_Autonomous_Vehicle_2024 Project'::'eRod_Autonomous_Vehicle_2024'::'Physical Architecture'::'Structure'::'Physical System'.'Sensors'.'Radar'.'68ec0773-d007-4df9-a136-9b6a2be6f8f9'); 
                             
                             
                        }  
                        ref :>> ownedPhysicalComponents =  ('eRod_Autonomous_Vehicle_2024 Project'::'eRod_Autonomous_Vehicle_2024'::'Physical Architecture'::'Structure'::'Physical System'.'Sensors'.'Camera',
                        'eRod_Autonomous_Vehicle_2024 Project'::'eRod_Autonomous_Vehicle_2024'::'Physical Architecture'::'Structure'::'Physical System'.'Sensors'.'Lidar',
                        'eRod_Autonomous_Vehicle_2024 Project'::'eRod_Autonomous_Vehicle_2024'::'Physical Architecture'::'Structure'::'Physical System'.'Sensors'.'Radar'); 
                         
                         
                    }  
                    part 'Left Front Tire' : PhysicalComponent { 
                        @CapellaID { eid = "51fc3db4-30ff-49a1-99d2-91f4839e4793"; } 
                        attribute :>> isAbstract = false; 
                        attribute :>> isActor = false; 
                        attribute :>> isHuman = false; 
                        attribute :>> kind = PhysicalComponentKind::UNSET; 
                        attribute :>> nature = PhysicalComponentNature::BEHAVIOR; 
                        allocation 'a9414300-77bc-4107-b463-58c70d4275f3' : ComponentFunctionalAllocation
                            allocate function ::> 'eRod_Autonomous_Vehicle_2024 Project'::'eRod_Autonomous_Vehicle_2024'::'Physical Architecture'::'Physical Functions'::'Root Physical Function'.'Steer Wheels'.'Force to Road Right Front'
                            to component ::> 'eRod_Autonomous_Vehicle_2024 Project'::'eRod_Autonomous_Vehicle_2024'::'Physical Architecture'::'Structure'::'Physical System'.'Left Front Tire';
                        perform 'eRod_Autonomous_Vehicle_2024 Project'::'eRod_Autonomous_Vehicle_2024'::'Physical Architecture'::'Physical Functions'::'Root Physical Function'.'Steer Wheels'.'Force to Road Right Front' ; 
                        port 'CP 2' : ComponentPort { 
                            @CapellaID { eid = "d92c7b30-d5e6-413b-a8bc-28709a783899"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                            ref allocation 'c660cfa1-2f5c-42c3-97f3-3d21efe8b78e' : PortAllocation
                                allocate allocatedPort ::> 'eRod_Autonomous_Vehicle_2024 Project'::'eRod_Autonomous_Vehicle_2024'::'Physical Architecture'::'Physical Functions'::'Root Physical Function'.'Steer Wheels'.'Force to Road Right Front'.'FIP 1'
                                to allocatingPort ::> 'eRod_Autonomous_Vehicle_2024 Project'::'eRod_Autonomous_Vehicle_2024'::'Physical Architecture'::'Structure'::'Physical System'.'Left Front Tire'.'CP 2'; 
                            ref :>> ownedPortAllocations =  ('eRod_Autonomous_Vehicle_2024 Project'::'eRod_Autonomous_Vehicle_2024'::'Physical Architecture'::'Structure'::'Physical System'.'Left Front Tire'.'CP 2'.'c660cfa1-2f5c-42c3-97f3-3d21efe8b78e'); 
                        }  
                        port 'CP 3' : ComponentPort { 
                            @CapellaID { eid = "31715b5d-b6d9-4571-8158-dee29bd52980"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                            ref allocation 'e3ffeaf3-7873-43f0-96d9-563ed13564fc' : PortAllocation
                                allocate allocatedPort ::> 'eRod_Autonomous_Vehicle_2024 Project'::'eRod_Autonomous_Vehicle_2024'::'Physical Architecture'::'Physical Functions'::'Root Physical Function'.'Steer Wheels'.'Force to Road Right Front'.'FOP 1'
                                to allocatingPort ::> 'eRod_Autonomous_Vehicle_2024 Project'::'eRod_Autonomous_Vehicle_2024'::'Physical Architecture'::'Structure'::'Physical System'.'Left Front Tire'.'CP 3'; 
                            ref :>> ownedPortAllocations =  ('eRod_Autonomous_Vehicle_2024 Project'::'eRod_Autonomous_Vehicle_2024'::'Physical Architecture'::'Structure'::'Physical System'.'Left Front Tire'.'CP 3'.'e3ffeaf3-7873-43f0-96d9-563ed13564fc'); 
                        }  
                        ref :>> ownedFunctionalAllocation =  ('eRod_Autonomous_Vehicle_2024 Project'::'eRod_Autonomous_Vehicle_2024'::'Physical Architecture'::'Structure'::'Physical System'.'Left Front Tire'.'a9414300-77bc-4107-b463-58c70d4275f3'); 
                    }  
                    part 'Right Front Tiier' : PhysicalComponent { 
                        @CapellaID { eid = "25782fbe-d130-4e73-9e8e-fafef48b2a2b"; } 
                        attribute :>> isAbstract = false; 
                        attribute :>> isActor = false; 
                        attribute :>> isHuman = false; 
                        attribute :>> kind = PhysicalComponentKind::UNSET; 
                        attribute :>> nature = PhysicalComponentNature::BEHAVIOR; 
                        allocation 'b22f87e6-eeb4-40fb-9f2f-f2b4d27cb8d7' : ComponentFunctionalAllocation
                            allocate function ::> 'eRod_Autonomous_Vehicle_2024 Project'::'eRod_Autonomous_Vehicle_2024'::'Physical Architecture'::'Physical Functions'::'Root Physical Function'.'Steer Wheels'.'Force to Road Left Front'
                            to component ::> 'eRod_Autonomous_Vehicle_2024 Project'::'eRod_Autonomous_Vehicle_2024'::'Physical Architecture'::'Structure'::'Physical System'.'Right Front Tiier';
                        perform 'eRod_Autonomous_Vehicle_2024 Project'::'eRod_Autonomous_Vehicle_2024'::'Physical Architecture'::'Physical Functions'::'Root Physical Function'.'Steer Wheels'.'Force to Road Left Front' ; 
                        port 'CP 1' : ComponentPort { 
                            @CapellaID { eid = "4f3bde75-2395-4e32-842e-f25f457ca015"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                            ref allocation '4ec29c62-1ef7-4915-9607-85eb79fdb274' : PortAllocation
                                allocate allocatedPort ::> 'eRod_Autonomous_Vehicle_2024 Project'::'eRod_Autonomous_Vehicle_2024'::'Physical Architecture'::'Physical Functions'::'Root Physical Function'.'Steer Wheels'.'Force to Road Left Front'.'FIP 1'
                                to allocatingPort ::> 'eRod_Autonomous_Vehicle_2024 Project'::'eRod_Autonomous_Vehicle_2024'::'Physical Architecture'::'Structure'::'Physical System'.'Right Front Tiier'.'CP 1'; 
                            ref :>> ownedPortAllocations =  ('eRod_Autonomous_Vehicle_2024 Project'::'eRod_Autonomous_Vehicle_2024'::'Physical Architecture'::'Structure'::'Physical System'.'Right Front Tiier'.'CP 1'.'4ec29c62-1ef7-4915-9607-85eb79fdb274'); 
                        }  
                        port 'CP 2' : ComponentPort { 
                            @CapellaID { eid = "075e9e95-88bc-46e2-94e7-bfcb87f1fe5b"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                            ref allocation '7f360e81-58f3-43da-83cb-1738fd9521e0' : PortAllocation
                                allocate allocatedPort ::> 'eRod_Autonomous_Vehicle_2024 Project'::'eRod_Autonomous_Vehicle_2024'::'Physical Architecture'::'Physical Functions'::'Root Physical Function'.'Steer Wheels'.'Force to Road Left Front'.'FOP 1'
                                to allocatingPort ::> 'eRod_Autonomous_Vehicle_2024 Project'::'eRod_Autonomous_Vehicle_2024'::'Physical Architecture'::'Structure'::'Physical System'.'Right Front Tiier'.'CP 2'; 
                            ref :>> ownedPortAllocations =  ('eRod_Autonomous_Vehicle_2024 Project'::'eRod_Autonomous_Vehicle_2024'::'Physical Architecture'::'Structure'::'Physical System'.'Right Front Tiier'.'CP 2'.'7f360e81-58f3-43da-83cb-1738fd9521e0'); 
                        }  
                        ref :>> ownedFunctionalAllocation =  ('eRod_Autonomous_Vehicle_2024 Project'::'eRod_Autonomous_Vehicle_2024'::'Physical Architecture'::'Structure'::'Physical System'.'Right Front Tiier'.'b22f87e6-eeb4-40fb-9f2f-f2b4d27cb8d7'); 
                    }  
                    part 'LSK' : PhysicalComponent { 
                        @CapellaID { eid = "5276b791-ff13-47f3-821c-2436faf574b6"; } 
                        attribute :>> isAbstract = false; 
                        attribute :>> isActor = false; 
                        attribute :>> isHuman = false; 
                        attribute :>> kind = PhysicalComponentKind::UNSET; 
                        attribute :>> nature = PhysicalComponentNature::BEHAVIOR; 
                        allocation '43db4713-463b-4d47-9277-9e70c9dc9e8b' : ComponentFunctionalAllocation
                            allocate function ::> 'eRod_Autonomous_Vehicle_2024 Project'::'eRod_Autonomous_Vehicle_2024'::'Physical Architecture'::'Physical Functions'::'Root Physical Function'.'Steer Wheels'.'Transmit Left Force'
                            to component ::> 'eRod_Autonomous_Vehicle_2024 Project'::'eRod_Autonomous_Vehicle_2024'::'Physical Architecture'::'Structure'::'Physical System'.'LSK';
                        perform 'eRod_Autonomous_Vehicle_2024 Project'::'eRod_Autonomous_Vehicle_2024'::'Physical Architecture'::'Physical Functions'::'Root Physical Function'.'Steer Wheels'.'Transmit Left Force' ; 
                        port 'CP 1' : ComponentPort { 
                            @CapellaID { eid = "aa7e4673-562f-419f-8f4a-bad00e2d5f26"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                            ref allocation '41f98a2d-2aa4-45e6-b108-ded8c84eba62' : PortAllocation
                                allocate allocatedPort ::> 'eRod_Autonomous_Vehicle_2024 Project'::'eRod_Autonomous_Vehicle_2024'::'Physical Architecture'::'Physical Functions'::'Root Physical Function'.'Steer Wheels'.'Transmit Left Force'.'FIP 1'
                                to allocatingPort ::> 'eRod_Autonomous_Vehicle_2024 Project'::'eRod_Autonomous_Vehicle_2024'::'Physical Architecture'::'Structure'::'Physical System'.'LSK'.'CP 1'; 
                            ref :>> ownedPortAllocations =  ('eRod_Autonomous_Vehicle_2024 Project'::'eRod_Autonomous_Vehicle_2024'::'Physical Architecture'::'Structure'::'Physical System'.'LSK'.'CP 1'.'41f98a2d-2aa4-45e6-b108-ded8c84eba62'); 
                        }  
                        port 'CP 2' : ComponentPort { 
                            @CapellaID { eid = "ceadfe07-627c-44df-9b73-ad590644dad6"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                            ref allocation '73e5f56e-219f-4acf-ba7e-c4fb39f8aa0a' : PortAllocation
                                allocate allocatedPort ::> 'eRod_Autonomous_Vehicle_2024 Project'::'eRod_Autonomous_Vehicle_2024'::'Physical Architecture'::'Physical Functions'::'Root Physical Function'.'Steer Wheels'.'Transmit Left Force'.'FOP 1'
                                to allocatingPort ::> 'eRod_Autonomous_Vehicle_2024 Project'::'eRod_Autonomous_Vehicle_2024'::'Physical Architecture'::'Structure'::'Physical System'.'LSK'.'CP 2'; 
                            ref :>> ownedPortAllocations =  ('eRod_Autonomous_Vehicle_2024 Project'::'eRod_Autonomous_Vehicle_2024'::'Physical Architecture'::'Structure'::'Physical System'.'LSK'.'CP 2'.'73e5f56e-219f-4acf-ba7e-c4fb39f8aa0a'); 
                        }  
                        ref :>> ownedFunctionalAllocation =  ('eRod_Autonomous_Vehicle_2024 Project'::'eRod_Autonomous_Vehicle_2024'::'Physical Architecture'::'Structure'::'Physical System'.'LSK'.'43db4713-463b-4d47-9277-9e70c9dc9e8b'); 
                    }  
                    part 'RSK' : PhysicalComponent { 
                        @CapellaID { eid = "ff93de31-da78-4f1f-bf78-30faa2a79280"; } 
                        attribute :>> isAbstract = false; 
                        attribute :>> isActor = false; 
                        attribute :>> isHuman = false; 
                        attribute :>> kind = PhysicalComponentKind::UNSET; 
                        attribute :>> nature = PhysicalComponentNature::BEHAVIOR; 
                        allocation '433c9606-5dd4-4f95-bc1a-b5963f5b7335' : ComponentFunctionalAllocation
                            allocate function ::> 'eRod_Autonomous_Vehicle_2024 Project'::'eRod_Autonomous_Vehicle_2024'::'Physical Architecture'::'Physical Functions'::'Root Physical Function'.'Steer Wheels'.'Transmit Right Force'
                            to component ::> 'eRod_Autonomous_Vehicle_2024 Project'::'eRod_Autonomous_Vehicle_2024'::'Physical Architecture'::'Structure'::'Physical System'.'RSK';
                        perform 'eRod_Autonomous_Vehicle_2024 Project'::'eRod_Autonomous_Vehicle_2024'::'Physical Architecture'::'Physical Functions'::'Root Physical Function'.'Steer Wheels'.'Transmit Right Force' ; 
                        port 'FRK' : ComponentPort { 
                            @CapellaID { eid = "cae2df70-4121-4ab6-b7af-1511f29719ee"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                            ref allocation '145013f8-dc2e-4b0c-99a4-389214e65c56' : PortAllocation
                                allocate allocatedPort ::> 'eRod_Autonomous_Vehicle_2024 Project'::'eRod_Autonomous_Vehicle_2024'::'Physical Architecture'::'Physical Functions'::'Root Physical Function'.'Steer Wheels'.'Transmit Right Force'.'FOP 3'
                                to allocatingPort ::> 'eRod_Autonomous_Vehicle_2024 Project'::'eRod_Autonomous_Vehicle_2024'::'Physical Architecture'::'Structure'::'Physical System'.'RSK'.'FRK'; 
                            ref :>> ownedPortAllocations =  ('eRod_Autonomous_Vehicle_2024 Project'::'eRod_Autonomous_Vehicle_2024'::'Physical Architecture'::'Structure'::'Physical System'.'RSK'.'FRK'.'145013f8-dc2e-4b0c-99a4-389214e65c56'); 
                        }  
                        port 'SM' : ComponentPort { 
                            @CapellaID { eid = "5cdc12f2-dffb-4923-82bc-1171bda058d6"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                            ref allocation '0327e752-b998-43e5-afab-c44fa0fb5a0c' : PortAllocation
                                allocate allocatedPort ::> 'eRod_Autonomous_Vehicle_2024 Project'::'eRod_Autonomous_Vehicle_2024'::'Physical Architecture'::'Physical Functions'::'Root Physical Function'.'Steer Wheels'.'Transmit Right Force'.'FIP 1'
                                to allocatingPort ::> 'eRod_Autonomous_Vehicle_2024 Project'::'eRod_Autonomous_Vehicle_2024'::'Physical Architecture'::'Structure'::'Physical System'.'RSK'.'SM'; 
                            ref :>> ownedPortAllocations =  ('eRod_Autonomous_Vehicle_2024 Project'::'eRod_Autonomous_Vehicle_2024'::'Physical Architecture'::'Structure'::'Physical System'.'RSK'.'SM'.'0327e752-b998-43e5-afab-c44fa0fb5a0c'); 
                        }  
                        ref :>> ownedFunctionalAllocation =  ('eRod_Autonomous_Vehicle_2024 Project'::'eRod_Autonomous_Vehicle_2024'::'Physical Architecture'::'Structure'::'Physical System'.'RSK'.'433c9606-5dd4-4f95-bc1a-b5963f5b7335'); 
                    }  
                    part 'Behavior for ADAS' : PhysicalComponent { 
                        @CapellaID { eid = "1e51716f-7da2-4967-bc03-634d69f107cf"; } 
                        attribute :>> isAbstract = false; 
                        attribute :>> isActor = false; 
                        attribute :>> isHuman = false; 
                        attribute :>> kind = PhysicalComponentKind::UNSET; 
                        attribute :>> nature = PhysicalComponentNature::BEHAVIOR; 
                        port 'Behavior for Vector__XXX' : ComponentPort { 
                            @CapellaID { eid = "fbdd8fb3-60fd-46e9-8092-5ee3020cfa4c"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::OUT; 
                            attribute :>> isUnique = false; 
                            ref :>> providedInterfaces =  ('eRod_Autonomous_Vehicle_2024 Project'::'eRod_Autonomous_Vehicle_2024'::'Physical Architecture'::'Interfaces'::'ADAS - Vector__XXX'); 
                        }  
                    }  
                    part 'Behavior for Vector__XXX' : PhysicalComponent { 
                        @CapellaID { eid = "a0f08d8d-4a5e-448b-862e-5fff271f17a6"; } 
                        attribute :>> isAbstract = false; 
                        attribute :>> isActor = false; 
                        attribute :>> isHuman = false; 
                        attribute :>> kind = PhysicalComponentKind::UNSET; 
                        attribute :>> nature = PhysicalComponentNature::BEHAVIOR; 
                        port 'Behavior for ADAS' : ComponentPort { 
                            @CapellaID { eid = "c32585f5-6191-4970-a590-8a4a2efec573"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> kind = ComponentPortKind::FLOW; 
                            attribute :>> isMaxInclusive = false; 
                            attribute :>> isMinInclusive = false; 
                            attribute :>> isOrdered = false; 
                            attribute :>> orientation = OrientationPortKind::IN; 
                            attribute :>> isUnique = false; 
                            ref :>> requiredInterfaces =  ('eRod_Autonomous_Vehicle_2024 Project'::'eRod_Autonomous_Vehicle_2024'::'Physical Architecture'::'Interfaces'::'ADAS - Vector__XXX'); 
                        }  
                    }  
                    part 'ADAS 1' : PhysicalComponent { 
                        @CapellaID { eid = "83c013f8-312e-4246-970f-852a3b5e39a9"; } 
                        attribute :>> isAbstract = false; 
                        attribute :>> isActor = false; 
                        attribute :>> isHuman = false; 
                        attribute :>> kind = PhysicalComponentKind::UNSET; 
                        attribute :>> nature = PhysicalComponentNature::NODE; 
                        part 'Behavior for ADAS' : PhysicalComponent { 
                            @CapellaID { eid = "ba78e98f-8259-467a-8176-2ca14bc75b15"; } 
                            attribute :>> isAbstract = false; 
                            attribute :>> isActor = false; 
                            attribute :>> isHuman = false; 
                            attribute :>> kind = PhysicalComponentKind::UNSET; 
                            attribute :>> nature = PhysicalComponentNature::BEHAVIOR; 
                            port 'Behavior for Vector__XXX' : ComponentPort { 
                                @CapellaID { eid = "5605b499-40e5-4f71-a437-a28f3aadd296"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                            }  
                        }  
                        port 'CAN_ACC' : PhysicalPort { 
                            @CapellaID { eid = "decab92a-9f18-4e6e-b517-0f4f2978610a"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '30e18713-26fe-4234-b8d2-b784a37ac4a1' : ComponentPortAllocation
                                allocate allocatedPort ::> 'eRod_Autonomous_Vehicle_2024 Project'::'eRod_Autonomous_Vehicle_2024'::'Physical Architecture'::'Structure'::'Physical System'.'ADAS 1'.'CAN_ACC'
                                to allocatingPort ::> 'eRod_Autonomous_Vehicle_2024 Project'::'eRod_Autonomous_Vehicle_2024'::'Physical Architecture'::'Structure'::'Physical System'.'ADAS 1'.'Behavior for ADAS'.'Behavior for Vector__XXX'; 
                            ref :>> ownedComponentPortAllocations =  ('eRod_Autonomous_Vehicle_2024 Project'::'eRod_Autonomous_Vehicle_2024'::'Physical Architecture'::'Structure'::'Physical System'.'ADAS 1'.'CAN_ACC'.'30e18713-26fe-4234-b8d2-b784a37ac4a1'); 
                        }  
                        ref :>> ownedPhysicalComponents =  ('eRod_Autonomous_Vehicle_2024 Project'::'eRod_Autonomous_Vehicle_2024'::'Physical Architecture'::'Structure'::'Physical System'.'ADAS 1'.'Behavior for ADAS'); 
                        allocation 'aa822b10-42f2-41b2-b97a-fdefe73575c0' : PartDeploymentLink
                            allocate deployed ::> 'eRod_Autonomous_Vehicle_2024 Project'::'eRod_Autonomous_Vehicle_2024'::'Physical Architecture'::'Structure'::'Physical System'.'ADAS 1'
                            to deploying ::> 'eRod_Autonomous_Vehicle_2024 Project'::'eRod_Autonomous_Vehicle_2024'::'Physical Architecture'::'Structure'::'Physical System'.'ADAS 1'.'Behavior for ADAS'; 
                    }  
                    part 'Vector__XXX 1' : PhysicalComponent { 
                        @CapellaID { eid = "1eca21ac-3f6c-4abe-b9f8-fcc2d90ee1e5"; } 
                        attribute :>> isAbstract = false; 
                        attribute :>> isActor = false; 
                        attribute :>> isHuman = false; 
                        attribute :>> kind = PhysicalComponentKind::UNSET; 
                        attribute :>> nature = PhysicalComponentNature::NODE; 
                        part 'Behavior for Vector__XXX' : PhysicalComponent { 
                            @CapellaID { eid = "d2f58845-d3cd-4113-ab3e-85d30e7cc88d"; } 
                            attribute :>> isAbstract = false; 
                            attribute :>> isActor = false; 
                            attribute :>> isHuman = false; 
                            attribute :>> kind = PhysicalComponentKind::UNSET; 
                            attribute :>> nature = PhysicalComponentNature::BEHAVIOR; 
                            port 'Behavior for ADAS' : ComponentPort { 
                                @CapellaID { eid = "0b133217-eb1c-4e41-9386-21bb0694bdcc"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                            }  
                        }  
                        port 'CAN_ACC' : PhysicalPort { 
                            @CapellaID { eid = "be43ff62-6145-4a7f-aa6b-a9a1757b4fa7"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '61d30a5c-79d9-4d32-92ef-ded4b4f290e9' : ComponentPortAllocation
                                allocate allocatedPort ::> 'eRod_Autonomous_Vehicle_2024 Project'::'eRod_Autonomous_Vehicle_2024'::'Physical Architecture'::'Structure'::'Physical System'.'Vector__XXX 1'.'CAN_ACC'
                                to allocatingPort ::> 'eRod_Autonomous_Vehicle_2024 Project'::'eRod_Autonomous_Vehicle_2024'::'Physical Architecture'::'Structure'::'Physical System'.'Vector__XXX 1'.'Behavior for Vector__XXX'.'Behavior for ADAS'; 
                            ref :>> ownedComponentPortAllocations =  ('eRod_Autonomous_Vehicle_2024 Project'::'eRod_Autonomous_Vehicle_2024'::'Physical Architecture'::'Structure'::'Physical System'.'Vector__XXX 1'.'CAN_ACC'.'61d30a5c-79d9-4d32-92ef-ded4b4f290e9'); 
                        }  
                        ref :>> ownedPhysicalComponents =  ('eRod_Autonomous_Vehicle_2024 Project'::'eRod_Autonomous_Vehicle_2024'::'Physical Architecture'::'Structure'::'Physical System'.'Vector__XXX 1'.'Behavior for Vector__XXX'); 
                        allocation '54364dac-3098-4c15-a5e4-fe91751e023a' : PartDeploymentLink
                            allocate deployed ::> 'eRod_Autonomous_Vehicle_2024 Project'::'eRod_Autonomous_Vehicle_2024'::'Physical Architecture'::'Structure'::'Physical System'.'Vector__XXX 1'
                            to deploying ::> 'eRod_Autonomous_Vehicle_2024 Project'::'eRod_Autonomous_Vehicle_2024'::'Physical Architecture'::'Structure'::'Physical System'.'Vector__XXX 1'.'Behavior for Vector__XXX'; 
                    }  
                    part 'CAN_ACC' : PhysicalComponent { 
                        @CapellaID { eid = "29b0d798-94d9-42b2-ac1e-e78d7566bd83"; } 
                        attribute :>> isAbstract = false; 
                        attribute :>> isActor = false; 
                        attribute :>> isHuman = false; 
                        attribute :>> kind = PhysicalComponentKind::UNSET; 
                        attribute :>> nature = PhysicalComponentNature::NODE; 
                        port 'ADAS' : PhysicalPort { 
                            @CapellaID { eid = "05e6e131-8fc8-4cf3-8abd-18f52573d291"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                        }  
                        port 'Vector__XXX' : PhysicalPort { 
                            @CapellaID { eid = "52bce6fb-6065-4a5b-84d9-965c8331f06d"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                        }  
                    }  
                    part 'ADAS 2' : PhysicalComponent { 
                        @CapellaID { eid = "aa32f9e1-eca6-478c-a71e-eaefae02aeef"; } 
                        attribute :>> isAbstract = false; 
                        attribute :>> isActor = false; 
                        attribute :>> isHuman = false; 
                        attribute :>> kind = PhysicalComponentKind::UNSET; 
                        attribute :>> nature = PhysicalComponentNature::NODE; 
                        part 'Behavior for ADAS' : PhysicalComponent { 
                            @CapellaID { eid = "921ae7f7-97e2-42d4-b24a-f520ae3512f9"; } 
                            attribute :>> isAbstract = false; 
                            attribute :>> isActor = false; 
                            attribute :>> isHuman = false; 
                            attribute :>> kind = PhysicalComponentKind::UNSET; 
                            attribute :>> nature = PhysicalComponentNature::BEHAVIOR; 
                            port 'Behavior for Vector__XXX' : ComponentPort { 
                                @CapellaID { eid = "8cfbb6d0-cf35-4146-95dc-41515e3dd67b"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::OUT; 
                                attribute :>> isUnique = false; 
                            }  
                        }  
                        port 'CAN_ACC' : PhysicalPort { 
                            @CapellaID { eid = "0512b799-d6df-4438-91a3-0d4580553b1d"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '4ac25cbb-39ff-4d72-b487-d3388a4707fc' : ComponentPortAllocation
                                allocate allocatedPort ::> 'eRod_Autonomous_Vehicle_2024 Project'::'eRod_Autonomous_Vehicle_2024'::'Physical Architecture'::'Structure'::'Physical System'.'ADAS 2'.'CAN_ACC'
                                to allocatingPort ::> 'eRod_Autonomous_Vehicle_2024 Project'::'eRod_Autonomous_Vehicle_2024'::'Physical Architecture'::'Structure'::'Physical System'.'ADAS 2'.'Behavior for ADAS'.'Behavior for Vector__XXX'; 
                            ref :>> ownedComponentPortAllocations =  ('eRod_Autonomous_Vehicle_2024 Project'::'eRod_Autonomous_Vehicle_2024'::'Physical Architecture'::'Structure'::'Physical System'.'ADAS 2'.'CAN_ACC'.'4ac25cbb-39ff-4d72-b487-d3388a4707fc'); 
                        }  
                        ref :>> ownedPhysicalComponents =  ('eRod_Autonomous_Vehicle_2024 Project'::'eRod_Autonomous_Vehicle_2024'::'Physical Architecture'::'Structure'::'Physical System'.'ADAS 2'.'Behavior for ADAS'); 
                        allocation '042214fc-435d-4850-b7ba-da0b21af2d05' : PartDeploymentLink
                            allocate deployed ::> 'eRod_Autonomous_Vehicle_2024 Project'::'eRod_Autonomous_Vehicle_2024'::'Physical Architecture'::'Structure'::'Physical System'.'ADAS 2'
                            to deploying ::> 'eRod_Autonomous_Vehicle_2024 Project'::'eRod_Autonomous_Vehicle_2024'::'Physical Architecture'::'Structure'::'Physical System'.'ADAS 2'.'Behavior for ADAS'; 
                    }  
                    part 'Vector__XXX 2' : PhysicalComponent { 
                        @CapellaID { eid = "6b738c11-80b3-4a2b-a762-506c279055ce"; } 
                        attribute :>> isAbstract = false; 
                        attribute :>> isActor = false; 
                        attribute :>> isHuman = false; 
                        attribute :>> kind = PhysicalComponentKind::UNSET; 
                        attribute :>> nature = PhysicalComponentNature::NODE; 
                        part 'Behavior for Vector__XXX' : PhysicalComponent { 
                            @CapellaID { eid = "824a3ce9-8904-4ccf-8ecb-df19f7eff71d"; } 
                            attribute :>> isAbstract = false; 
                            attribute :>> isActor = false; 
                            attribute :>> isHuman = false; 
                            attribute :>> kind = PhysicalComponentKind::UNSET; 
                            attribute :>> nature = PhysicalComponentNature::BEHAVIOR; 
                            port 'Behavior for ADAS' : ComponentPort { 
                                @CapellaID { eid = "b20fea1b-1c50-4c84-8352-3328487a6ebc"; } 
                                attribute :>> aggregationKind = AggregationKind::UNSET; 
                                attribute :>> isFinal = false; 
                                attribute :>> isAbstract = false; 
                                attribute :>> isDerived = false; 
                                attribute :>> isPartOfKey = false; 
                                attribute :>> isReadOnly = false; 
                                attribute :>> isStatic = false; 
                                attribute :>> kind = ComponentPortKind::FLOW; 
                                attribute :>> isMaxInclusive = false; 
                                attribute :>> isMinInclusive = false; 
                                attribute :>> isOrdered = false; 
                                attribute :>> orientation = OrientationPortKind::IN; 
                                attribute :>> isUnique = false; 
                            }  
                        }  
                        port 'CAN_ACC' : PhysicalPort { 
                            @CapellaID { eid = "be04f152-3a41-4b47-b152-2bd0e20d0355"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                            ref allocation '6ffd3ce5-25c1-46f5-a270-d62b80211a4c' : ComponentPortAllocation
                                allocate allocatedPort ::> 'eRod_Autonomous_Vehicle_2024 Project'::'eRod_Autonomous_Vehicle_2024'::'Physical Architecture'::'Structure'::'Physical System'.'Vector__XXX 2'.'CAN_ACC'
                                to allocatingPort ::> 'eRod_Autonomous_Vehicle_2024 Project'::'eRod_Autonomous_Vehicle_2024'::'Physical Architecture'::'Structure'::'Physical System'.'Vector__XXX 2'.'Behavior for Vector__XXX'.'Behavior for ADAS'; 
                            ref :>> ownedComponentPortAllocations =  ('eRod_Autonomous_Vehicle_2024 Project'::'eRod_Autonomous_Vehicle_2024'::'Physical Architecture'::'Structure'::'Physical System'.'Vector__XXX 2'.'CAN_ACC'.'6ffd3ce5-25c1-46f5-a270-d62b80211a4c'); 
                        }  
                        ref :>> ownedPhysicalComponents =  ('eRod_Autonomous_Vehicle_2024 Project'::'eRod_Autonomous_Vehicle_2024'::'Physical Architecture'::'Structure'::'Physical System'.'Vector__XXX 2'.'Behavior for Vector__XXX'); 
                        allocation 'f6a9d889-9458-4b85-afa2-d2bec4090ea4' : PartDeploymentLink
                            allocate deployed ::> 'eRod_Autonomous_Vehicle_2024 Project'::'eRod_Autonomous_Vehicle_2024'::'Physical Architecture'::'Structure'::'Physical System'.'Vector__XXX 2'
                            to deploying ::> 'eRod_Autonomous_Vehicle_2024 Project'::'eRod_Autonomous_Vehicle_2024'::'Physical Architecture'::'Structure'::'Physical System'.'Vector__XXX 2'.'Behavior for Vector__XXX'; 
                    }  
                    part 'CAN_ACC2' : PhysicalComponent { 
                        @CapellaID { eid = "d9160654-32cf-4326-a77b-de334859100a"; } 
                        attribute :>> isAbstract = false; 
                        attribute :>> isActor = false; 
                        attribute :>> isHuman = false; 
                        attribute :>> kind = PhysicalComponentKind::UNSET; 
                        attribute :>> nature = PhysicalComponentNature::NODE; 
                        port 'ADAS' : PhysicalPort { 
                            @CapellaID { eid = "f8ba083a-5386-488e-853c-f249965ab5e4"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                        }  
                        port 'Vector__XXX' : PhysicalPort { 
                            @CapellaID { eid = "91d65fac-2ae6-49a5-b5a5-25050ec68030"; } 
                            attribute :>> aggregationKind = AggregationKind::UNSET; 
                            attribute :>> isFinal = false; 
                            attribute :>> isAbstract = false; 
                            attribute :>> isDerived = false; 
                            attribute :>> isPartOfKey = false; 
                            attribute :>> isReadOnly = false; 
                            attribute :>> isStatic = false; 
                            attribute :>> isMaxInclusive = false; 
                            attribute :>> isMinInclusive = false; 
                            attribute :>> isOrdered = false; 
                            attribute :>> isUnique = false; 
                        }  
                    }  
                    port 'CP 2' : ComponentPort { 
                        @CapellaID { eid = "4297f336-4d70-4c95-bdfb-d62da3fc3d46"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                         
                    }  
                    port 'CP 1' : ComponentPort { 
                        @CapellaID { eid = "1f1c787a-d716-489a-b424-c4f517d1e81b"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                         
                    }  
                    port 'CP 6' : ComponentPort { 
                        @CapellaID { eid = "cafa67d1-6a22-4e66-b139-d1f994a376ed"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                         
                    }  
                    port 'CP 7' : ComponentPort { 
                        @CapellaID { eid = "7a7fb929-0823-416f-8bb2-bc3b62784f7f"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                         
                    }  
                    interface '9ffd32eb-a9e2-4713-849e-591a27a1be50' : ComponentExchange 
                        connect source ::> 'eRod_Autonomous_Vehicle_2024 Project'::'eRod_Autonomous_Vehicle_2024'::'Physical Architecture'::'Structure'::'Physical System'.'Steer Torque Sensor'.'CP 1'
                        to  target ::> 'eRod_Autonomous_Vehicle_2024 Project'::'eRod_Autonomous_Vehicle_2024'::'Physical Architecture'::'Structure'::'Physical System'.'EPS Controller'.'CP 3' { 
                        @CapellaID { eid = "9ffd32eb-a9e2-4713-849e-591a27a1be50"; } 
                        attribute :>> kind = ComponentExchangeKind::FLOW; 
                        attribute :>> interfaceName = "Steering"; 
                        attribute :>> isOriented = false; 
                        allocation '1d754f05-190a-40f9-88e7-e7f165160aaf' : ComponentExchangeFunctionalExchangeAllocation
                            allocate functionalExchange ::> 'eRod_Autonomous_Vehicle_2024 Project'::'eRod_Autonomous_Vehicle_2024'::'Physical Architecture'::'Physical Functions'::'Root Physical Function'.'6b77677c-6a80-4a58-a5ea-6922399b4ff9'
                            to componentExchange ::> 'eRod_Autonomous_Vehicle_2024 Project'::'eRod_Autonomous_Vehicle_2024'::'Physical Architecture'::'Structure'::'Physical System'.'9ffd32eb-a9e2-4713-849e-591a27a1be50'; 
                        allocation '071f11fc-ea86-48a0-bbc4-af4f933ef212' : ComponentExchangeFunctionalExchangeAllocation
                            allocate functionalExchange ::> 'eRod_Autonomous_Vehicle_2024 Project'::'eRod_Autonomous_Vehicle_2024'::'Physical Architecture'::'Physical Functions'::'Root Physical Function'.'Steer Wheels'.'73d30128-b552-4b75-a646-c889356202be'
                            to componentExchange ::> 'eRod_Autonomous_Vehicle_2024 Project'::'eRod_Autonomous_Vehicle_2024'::'Physical Architecture'::'Structure'::'Physical System'.'9ffd32eb-a9e2-4713-849e-591a27a1be50'; 
                        ref :>> ownedComponentExchangeFunctionalExchangeAllocations =  ('eRod_Autonomous_Vehicle_2024 Project'::'eRod_Autonomous_Vehicle_2024'::'Physical Architecture'::'Structure'::'Physical System'.'9ffd32eb-a9e2-4713-849e-591a27a1be50'.'1d754f05-190a-40f9-88e7-e7f165160aaf',
                        'eRod_Autonomous_Vehicle_2024 Project'::'eRod_Autonomous_Vehicle_2024'::'Physical Architecture'::'Structure'::'Physical System'.'9ffd32eb-a9e2-4713-849e-591a27a1be50'.'071f11fc-ea86-48a0-bbc4-af4f933ef212'); 
                    }  
                    interface 'aa2ed6bd-15bd-495e-9291-ca083e5bff59' : ComponentExchange 
                        connect source ::> 'eRod_Autonomous_Vehicle_2024 Project'::'eRod_Autonomous_Vehicle_2024'::'Physical Architecture'::'Structure'::'Physical System'.'EPS Controller'.'CP 4'
                        to  target ::> 'eRod_Autonomous_Vehicle_2024 Project'::'eRod_Autonomous_Vehicle_2024'::'Physical Architecture'::'Structure'::'Physical System'.'Motor Controller'.'CP 1' { 
                        @CapellaID { eid = "aa2ed6bd-15bd-495e-9291-ca083e5bff59"; } 
                        attribute :>> kind = ComponentExchangeKind::FLOW; 
                        attribute :>> interfaceName = "Steering Commands"; 
                        attribute :>> isOriented = false; 
                        allocation '52aaff37-16e6-46c3-a7b6-bbb0b7f2b53a' : ComponentExchangeFunctionalExchangeAllocation
                            allocate functionalExchange ::> 'eRod_Autonomous_Vehicle_2024 Project'::'eRod_Autonomous_Vehicle_2024'::'Physical Architecture'::'Physical Functions'::'Root Physical Function'.'9d9dee37-2079-419b-b8a5-dd75d6999ad4'
                            to componentExchange ::> 'eRod_Autonomous_Vehicle_2024 Project'::'eRod_Autonomous_Vehicle_2024'::'Physical Architecture'::'Structure'::'Physical System'.'aa2ed6bd-15bd-495e-9291-ca083e5bff59'; 
                        ref :>> ownedComponentExchangeFunctionalExchangeAllocations =  ('eRod_Autonomous_Vehicle_2024 Project'::'eRod_Autonomous_Vehicle_2024'::'Physical Architecture'::'Structure'::'Physical System'.'aa2ed6bd-15bd-495e-9291-ca083e5bff59'.'52aaff37-16e6-46c3-a7b6-bbb0b7f2b53a'); 
                    }  
                    interface '3e0faeb6-3abb-44bf-a7a4-b7b1ae2614b2' : ComponentExchange 
                        connect source ::> 'eRod_Autonomous_Vehicle_2024 Project'::'eRod_Autonomous_Vehicle_2024'::'Physical Architecture'::'Structure'::'Physical System'.'AV Controller'.'CP 1'
                        to  target ::> 'eRod_Autonomous_Vehicle_2024 Project'::'eRod_Autonomous_Vehicle_2024'::'Physical Architecture'::'Structure'::'Physical System'.'EPS Controller'.'CP 5' { 
                        @CapellaID { eid = "3e0faeb6-3abb-44bf-a7a4-b7b1ae2614b2"; } 
                        attribute :>> kind = ComponentExchangeKind::FLOW; 
                        attribute :>> interfaceName = "Steering Control"; 
                        attribute :>> isOriented = false; 
                    }  
                    interface '97909a2b-85b9-4560-97ce-d0f8e3934656' : ComponentExchange 
                        connect source ::> 'eRod_Autonomous_Vehicle_2024 Project'::'eRod_Autonomous_Vehicle_2024'::'Physical Architecture'::'Structure'::'Physical System'.'Brake Controller'.'CP 1'
                        to  target ::> 'eRod_Autonomous_Vehicle_2024 Project'::'eRod_Autonomous_Vehicle_2024'::'Physical Architecture'::'Structure'::'Physical System'.'AV Controller'.'CP 3' { 
                        @CapellaID { eid = "97909a2b-85b9-4560-97ce-d0f8e3934656"; } 
                        attribute :>> kind = ComponentExchangeKind::FLOW; 
                        attribute :>> interfaceName = "Brake Commands"; 
                        attribute :>> isOriented = false; 
                    }  
                    interface 'd9dba508-025e-487c-9364-f9fc08dc4dbe' : ComponentExchange 
                        connect source ::> 'eRod_Autonomous_Vehicle_2024 Project'::'eRod_Autonomous_Vehicle_2024'::'Physical Architecture'::'Structure'::'Physical System'.'Motor Controller'.'CP 2'
                        to  target ::> 'eRod_Autonomous_Vehicle_2024 Project'::'eRod_Autonomous_Vehicle_2024'::'Physical Architecture'::'Structure'::'Physical System'.'LSK'.'CP 1' { 
                        @CapellaID { eid = "d9dba508-025e-487c-9364-f9fc08dc4dbe"; } 
                        attribute :>> kind = ComponentExchangeKind::FLOW; 
                        attribute :>> interfaceName = "C 8"; 
                        attribute :>> isOriented = false; 
                        allocation '331394d0-8fe1-49f7-81fa-94613aeb4d80' : ComponentExchangeFunctionalExchangeAllocation
                            allocate functionalExchange ::> 'eRod_Autonomous_Vehicle_2024 Project'::'eRod_Autonomous_Vehicle_2024'::'Physical Architecture'::'Physical Functions'::'Root Physical Function'.'Steer Wheels'.'2a944e7a-8965-4971-870b-df89fc55c7dd'
                            to componentExchange ::> 'eRod_Autonomous_Vehicle_2024 Project'::'eRod_Autonomous_Vehicle_2024'::'Physical Architecture'::'Structure'::'Physical System'.'d9dba508-025e-487c-9364-f9fc08dc4dbe'; 
                        ref :>> ownedComponentExchangeFunctionalExchangeAllocations =  ('eRod_Autonomous_Vehicle_2024 Project'::'eRod_Autonomous_Vehicle_2024'::'Physical Architecture'::'Structure'::'Physical System'.'d9dba508-025e-487c-9364-f9fc08dc4dbe'.'331394d0-8fe1-49f7-81fa-94613aeb4d80'); 
                    }  
                    interface '31d5cadb-4943-4566-917d-7b582c019bc3' : ComponentExchange 
                        connect source ::> 'eRod_Autonomous_Vehicle_2024 Project'::'eRod_Autonomous_Vehicle_2024'::'Physical Architecture'::'Structure'::'Physical System'.'Motor Controller'.'CP 3'
                        to  target ::> 'eRod_Autonomous_Vehicle_2024 Project'::'eRod_Autonomous_Vehicle_2024'::'Physical Architecture'::'Structure'::'Physical System'.'RSK'.'SM' { 
                        @CapellaID { eid = "31d5cadb-4943-4566-917d-7b582c019bc3"; } 
                        attribute :>> kind = ComponentExchangeKind::FLOW; 
                        attribute :>> interfaceName = "SM-RSK"; 
                        attribute :>> isOriented = false; 
                        allocation 'b86e9320-d282-4b1a-9505-e623466baa65' : ComponentExchangeFunctionalExchangeAllocation
                            allocate functionalExchange ::> 'eRod_Autonomous_Vehicle_2024 Project'::'eRod_Autonomous_Vehicle_2024'::'Physical Architecture'::'Physical Functions'::'Root Physical Function'.'Steer Wheels'.'872387bc-c61f-4975-bf12-dd220518b44d'
                            to componentExchange ::> 'eRod_Autonomous_Vehicle_2024 Project'::'eRod_Autonomous_Vehicle_2024'::'Physical Architecture'::'Structure'::'Physical System'.'31d5cadb-4943-4566-917d-7b582c019bc3'; 
                        ref :>> ownedComponentExchangeFunctionalExchangeAllocations =  ('eRod_Autonomous_Vehicle_2024 Project'::'eRod_Autonomous_Vehicle_2024'::'Physical Architecture'::'Structure'::'Physical System'.'31d5cadb-4943-4566-917d-7b582c019bc3'.'b86e9320-d282-4b1a-9505-e623466baa65'); 
                    }  
                    interface '672839a9-69f4-4e5e-96d0-d96dc77337db' : ComponentExchange 
                        connect source ::> 'eRod_Autonomous_Vehicle_2024 Project'::'eRod_Autonomous_Vehicle_2024'::'Physical Architecture'::'Structure'::'Physical System'.'RSK'.'FRK'
                        to  target ::> 'eRod_Autonomous_Vehicle_2024 Project'::'eRod_Autonomous_Vehicle_2024'::'Physical Architecture'::'Structure'::'Physical System'.'Left Front Tire'.'CP 2' { 
                        @CapellaID { eid = "672839a9-69f4-4e5e-96d0-d96dc77337db"; } 
                        attribute :>> kind = ComponentExchangeKind::FLOW; 
                        attribute :>> interfaceName = "RSK-FRK"; 
                        attribute :>> isOriented = false; 
                        allocation '662a752e-6af7-4414-95c6-23cb906f55f7' : ComponentExchangeFunctionalExchangeAllocation
                            allocate functionalExchange ::> 'eRod_Autonomous_Vehicle_2024 Project'::'eRod_Autonomous_Vehicle_2024'::'Physical Architecture'::'Physical Functions'::'Root Physical Function'.'Steer Wheels'.'a9b2c213-d86e-4c47-a6f3-8f6216ccdb49'
                            to componentExchange ::> 'eRod_Autonomous_Vehicle_2024 Project'::'eRod_Autonomous_Vehicle_2024'::'Physical Architecture'::'Structure'::'Physical System'.'672839a9-69f4-4e5e-96d0-d96dc77337db'; 
                        ref :>> ownedComponentExchangeFunctionalExchangeAllocations =  ('eRod_Autonomous_Vehicle_2024 Project'::'eRod_Autonomous_Vehicle_2024'::'Physical Architecture'::'Structure'::'Physical System'.'672839a9-69f4-4e5e-96d0-d96dc77337db'.'662a752e-6af7-4414-95c6-23cb906f55f7'); 
                    }  
                    interface '36cc4948-71d7-403d-8350-93cc284b6a54' : ComponentExchange 
                        connect source ::> 'eRod_Autonomous_Vehicle_2024 Project'::'eRod_Autonomous_Vehicle_2024'::'Physical Architecture'::'Structure'::'Physical System'.'LSK'.'CP 2'
                        to  target ::> 'eRod_Autonomous_Vehicle_2024 Project'::'eRod_Autonomous_Vehicle_2024'::'Physical Architecture'::'Structure'::'Physical System'.'Right Front Tiier'.'CP 1' { 
                        @CapellaID { eid = "36cc4948-71d7-403d-8350-93cc284b6a54"; } 
                        attribute :>> kind = ComponentExchangeKind::FLOW; 
                        attribute :>> interfaceName = "C 11"; 
                        attribute :>> isOriented = false; 
                        allocation '63d88821-eeff-4fde-b8f7-883aa3a53a89' : ComponentExchangeFunctionalExchangeAllocation
                            allocate functionalExchange ::> 'eRod_Autonomous_Vehicle_2024 Project'::'eRod_Autonomous_Vehicle_2024'::'Physical Architecture'::'Physical Functions'::'Root Physical Function'.'Steer Wheels'.'4ab23e81-867a-4e42-b992-a665c9ce5324'
                            to componentExchange ::> 'eRod_Autonomous_Vehicle_2024 Project'::'eRod_Autonomous_Vehicle_2024'::'Physical Architecture'::'Structure'::'Physical System'.'36cc4948-71d7-403d-8350-93cc284b6a54'; 
                        ref :>> ownedComponentExchangeFunctionalExchangeAllocations =  ('eRod_Autonomous_Vehicle_2024 Project'::'eRod_Autonomous_Vehicle_2024'::'Physical Architecture'::'Structure'::'Physical System'.'36cc4948-71d7-403d-8350-93cc284b6a54'.'63d88821-eeff-4fde-b8f7-883aa3a53a89'); 
                    }  
                    interface '56562dd2-af0d-47ff-83b3-3a49f704709b' : ComponentExchange 
                        connect source ::> 'eRod_Autonomous_Vehicle_2024 Project'::'eRod_Autonomous_Vehicle_2024'::'Physical Architecture'::'Structure'::'Physical System'.'Behavior for ADAS'.'Behavior for Vector__XXX'
                        to  target ::> 'eRod_Autonomous_Vehicle_2024 Project'::'eRod_Autonomous_Vehicle_2024'::'Physical Architecture'::'Structure'::'Physical System'.'Behavior for Vector__XXX'.'Behavior for ADAS' { 
                        @CapellaID { eid = "56562dd2-af0d-47ff-83b3-3a49f704709b"; } 
                        attribute :>> kind = ComponentExchangeKind::FLOW; 
                        attribute :>> interfaceName = "ADAS - Vector__XXX"; 
                        attribute :>> isOriented = false; 
                        ref :>> convoyedInformations =  ('eRod_Autonomous_Vehicle_2024 Project'::'eRod_Autonomous_Vehicle_2024'::'Physical Architecture'::'Data'::'ADAS'::'ADAS_ACC_Frame'); 
                    }  
                    interface '58155f7a-62cb-4f20-ab94-a0b8577c02cd' : ComponentExchange 
                        connect source ::> 'eRod_Autonomous_Vehicle_2024 Project'::'eRod_Autonomous_Vehicle_2024'::'Physical Architecture'::'Structure'::'Physical System'.'ADAS 1'.'Behavior for ADAS'.'Behavior for Vector__XXX'
                        to  target ::> 'eRod_Autonomous_Vehicle_2024 Project'::'eRod_Autonomous_Vehicle_2024'::'Physical Architecture'::'Structure'::'Physical System'.'Vector__XXX 1'.'Behavior for Vector__XXX'.'Behavior for ADAS' { 
                        @CapellaID { eid = "58155f7a-62cb-4f20-ab94-a0b8577c02cd"; } 
                        attribute :>> kind = ComponentExchangeKind::FLOW; 
                        attribute :>> interfaceName = "ADAS - Vector__XXX"; 
                        attribute :>> isOriented = false; 
                    }  
                    interface 'b93eb18f-408f-4247-a311-a00d2ab84698' : ComponentExchange 
                        connect source ::> 'eRod_Autonomous_Vehicle_2024 Project'::'eRod_Autonomous_Vehicle_2024'::'Physical Architecture'::'Structure'::'Physical System'.'ADAS 2'.'Behavior for ADAS'.'Behavior for Vector__XXX'
                        to  target ::> 'eRod_Autonomous_Vehicle_2024 Project'::'eRod_Autonomous_Vehicle_2024'::'Physical Architecture'::'Structure'::'Physical System'.'Vector__XXX 2'.'Behavior for Vector__XXX'.'Behavior for ADAS' { 
                        @CapellaID { eid = "b93eb18f-408f-4247-a311-a00d2ab84698"; } 
                        attribute :>> kind = ComponentExchangeKind::FLOW; 
                        attribute :>> interfaceName = "ADAS - Vector__XXX"; 
                        attribute :>> isOriented = false; 
                    }  
                    interface 'fa66c2fc-7d9e-4baf-b3a4-470bfe8704c9' : PhysicalLink 
                        connect sourcePhysicalPort ::> 'eRod_Autonomous_Vehicle_2024 Project'::'eRod_Autonomous_Vehicle_2024'::'Physical Architecture'::'Structure'::'Physical System'.'eRod'.'Brakes'.'Brake Boosster'.'PP 1'
                        to targetPhysicalPort ::> 'eRod_Autonomous_Vehicle_2024 Project'::'eRod_Autonomous_Vehicle_2024'::'Physical Architecture'::'Structure'::'Physical System'.'eRod'.'Brakes'.'Brake Caliper Front Left'.'PP 1' {
                        @CapellaID { eid = "fa66c2fc-7d9e-4baf-b3a4-470bfe8704c9"; } 
                        attribute :>> interfaceName = "HYD"; 
                    }  
                    interface '5f77d53c-7a14-4272-885c-4edeb96e8ec0' : PhysicalLink 
                        connect sourcePhysicalPort ::> 'eRod_Autonomous_Vehicle_2024 Project'::'eRod_Autonomous_Vehicle_2024'::'Physical Architecture'::'Structure'::'Physical System'.'eRod'.'Brakes'.'Brake Boosster'.'PP 2'
                        to targetPhysicalPort ::> 'eRod_Autonomous_Vehicle_2024 Project'::'eRod_Autonomous_Vehicle_2024'::'Physical Architecture'::'Structure'::'Physical System'.'eRod'.'Brakes'.'Brake Caliper Front Right'.'PP 1' {
                        @CapellaID { eid = "5f77d53c-7a14-4272-885c-4edeb96e8ec0"; } 
                        attribute :>> interfaceName = "HYD"; 
                    }  
                    interface '1ece2115-0f21-4201-920a-9d1fd6e2d2f2' : PhysicalLink 
                        connect sourcePhysicalPort ::> 'eRod_Autonomous_Vehicle_2024 Project'::'eRod_Autonomous_Vehicle_2024'::'Physical Architecture'::'Structure'::'Physical System'.'eRod'.'Brakes'.'Brake Boosster'.'PP 3'
                        to targetPhysicalPort ::> 'eRod_Autonomous_Vehicle_2024 Project'::'eRod_Autonomous_Vehicle_2024'::'Physical Architecture'::'Structure'::'Physical System'.'eRod'.'Brakes'.'Brake Caliper Rear Right'.'PP 1' {
                        @CapellaID { eid = "1ece2115-0f21-4201-920a-9d1fd6e2d2f2"; } 
                        attribute :>> interfaceName = "HYD"; 
                    }  
                    interface '3d2dc7a8-eb87-4bd8-917b-26edf8282173' : PhysicalLink 
                        connect sourcePhysicalPort ::> 'eRod_Autonomous_Vehicle_2024 Project'::'eRod_Autonomous_Vehicle_2024'::'Physical Architecture'::'Structure'::'Physical System'.'eRod'.'Brakes'.'Brake Boosster'.'PP 4'
                        to targetPhysicalPort ::> 'eRod_Autonomous_Vehicle_2024 Project'::'eRod_Autonomous_Vehicle_2024'::'Physical Architecture'::'Structure'::'Physical System'.'eRod'.'Brakes'.'Brake Caliper Rear Left'.'PP 1' {
                        @CapellaID { eid = "3d2dc7a8-eb87-4bd8-917b-26edf8282173"; } 
                        attribute :>> interfaceName = "HYD"; 
                    }  
                    interface '111053f0-bb7e-439a-890f-5a09787be4fa' : PhysicalLink 
                        connect sourcePhysicalPort ::> 'eRod_Autonomous_Vehicle_2024 Project'::'eRod_Autonomous_Vehicle_2024'::'Physical Architecture'::'Structure'::'Physical System'.'eRod'.'Brake Pedal'.'PP 2'
                        to targetPhysicalPort ::> 'eRod_Autonomous_Vehicle_2024 Project'::'eRod_Autonomous_Vehicle_2024'::'Physical Architecture'::'Structure'::'Physical System'.'eRod'.'Brakes'.'Brake Boosster'.'PP 5' {
                        @CapellaID { eid = "111053f0-bb7e-439a-890f-5a09787be4fa"; } 
                        attribute :>> interfaceName = "Brake Force"; 
                    }  
                    interface 'e80405bd-2829-413e-a61c-046f8de2bfb8' : PhysicalLink 
                        connect sourcePhysicalPort ::> 'eRod_Autonomous_Vehicle_2024 Project'::'eRod_Autonomous_Vehicle_2024'::'Physical Architecture'::'Structure'::'Physical System'.'eRod'.'Brakes'.'Brake Caliper Front Right'.'PP 2'
                        to targetPhysicalPort ::> 'eRod_Autonomous_Vehicle_2024 Project'::'eRod_Autonomous_Vehicle_2024'::'Physical Architecture'::'Structure'::'Physical System'.'eRod'.'Brakes'.'Brake Fluid Container'.'PP 1' {
                        @CapellaID { eid = "e80405bd-2829-413e-a61c-046f8de2bfb8"; } 
                        attribute :>> interfaceName = "HYD"; 
                    }  
                    interface 'b28da93e-075b-43df-920c-6ab71e3e5b38' : PhysicalLink 
                        connect sourcePhysicalPort ::> 'eRod_Autonomous_Vehicle_2024 Project'::'eRod_Autonomous_Vehicle_2024'::'Physical Architecture'::'Structure'::'Physical System'.'eRod'.'Brakes'.'Brake Caliper Front Left'.'PP 2'
                        to targetPhysicalPort ::> 'eRod_Autonomous_Vehicle_2024 Project'::'eRod_Autonomous_Vehicle_2024'::'Physical Architecture'::'Structure'::'Physical System'.'eRod'.'Brakes'.'Brake Fluid Container'.'PP 2' {
                        @CapellaID { eid = "b28da93e-075b-43df-920c-6ab71e3e5b38"; } 
                        attribute :>> interfaceName = "HYD"; 
                    }  
                    interface 'ff5d44db-3b7f-4856-bdfb-2ce09c9f967c' : PhysicalLink 
                        connect sourcePhysicalPort ::> 'eRod_Autonomous_Vehicle_2024 Project'::'eRod_Autonomous_Vehicle_2024'::'Physical Architecture'::'Structure'::'Physical System'.'eRod'.'Brakes'.'Brake Caliper Rear Right'.'PP 2'
                        to targetPhysicalPort ::> 'eRod_Autonomous_Vehicle_2024 Project'::'eRod_Autonomous_Vehicle_2024'::'Physical Architecture'::'Structure'::'Physical System'.'eRod'.'Brakes'.'Brake Fluid Container'.'PP 3' {
                        @CapellaID { eid = "ff5d44db-3b7f-4856-bdfb-2ce09c9f967c"; } 
                        attribute :>> interfaceName = "HYD"; 
                    }  
                    interface '3846568f-4f29-4d65-99ff-ae6e5baccacd' : PhysicalLink 
                        connect sourcePhysicalPort ::> 'eRod_Autonomous_Vehicle_2024 Project'::'eRod_Autonomous_Vehicle_2024'::'Physical Architecture'::'Structure'::'Physical System'.'eRod'.'Brakes'.'Brake Caliper Rear Left'.'PP 2'
                        to targetPhysicalPort ::> 'eRod_Autonomous_Vehicle_2024 Project'::'eRod_Autonomous_Vehicle_2024'::'Physical Architecture'::'Structure'::'Physical System'.'eRod'.'Brakes'.'Brake Fluid Container'.'PP 4' {
                        @CapellaID { eid = "3846568f-4f29-4d65-99ff-ae6e5baccacd"; } 
                        attribute :>> interfaceName = "HYD"; 
                    }  
                    interface '9e6431dc-6fda-4de1-b76c-b9217285bbdb' : PhysicalLink 
                        connect sourcePhysicalPort ::> 'eRod_Autonomous_Vehicle_2024 Project'::'eRod_Autonomous_Vehicle_2024'::'Physical Architecture'::'Structure'::'Physical System'.'eRod'.'Brakes'.'Brake Fluid Container'.'PP 5'
                        to targetPhysicalPort ::> 'eRod_Autonomous_Vehicle_2024 Project'::'eRod_Autonomous_Vehicle_2024'::'Physical Architecture'::'Structure'::'Physical System'.'eRod'.'Brakes'.'Brake Boosster'.'PP 6' {
                        @CapellaID { eid = "9e6431dc-6fda-4de1-b76c-b9217285bbdb"; } 
                        attribute :>> interfaceName = "HYD"; 
                    }  
                    interface '474abfa8-8b0c-41bf-8c17-450a02b1aa44' : PhysicalLink 
                        connect sourcePhysicalPort ::> 'eRod_Autonomous_Vehicle_2024 Project'::'eRod_Autonomous_Vehicle_2024'::'Physical Architecture'::'Structure'::'Physical System'.'eRod'.'Brake Pedal'.'PP 3'
                        to targetPhysicalPort ::> 'eRod_Autonomous_Vehicle_2024 Project'::'eRod_Autonomous_Vehicle_2024'::'Physical Architecture'::'Structure'::'Physical System'.'eRod'.'Brake solenoid'.'PP 1' {
                        @CapellaID { eid = "474abfa8-8b0c-41bf-8c17-450a02b1aa44"; } 
                        attribute :>> interfaceName = "Wire"; 
                    }  
                    interface '7eb77bd7-843b-4558-9051-3bcc6b17db3a' : PhysicalLink 
                        connect sourcePhysicalPort ::> 'eRod_Autonomous_Vehicle_2024 Project'::'eRod_Autonomous_Vehicle_2024'::'Physical Architecture'::'Structure'::'Physical System'.'eRod'.'Brake Controller'.'PP 1'
                        to targetPhysicalPort ::> 'eRod_Autonomous_Vehicle_2024 Project'::'eRod_Autonomous_Vehicle_2024'::'Physical Architecture'::'Structure'::'Physical System'.'eRod'.'Brake solenoid'.'PP 4' {
                        @CapellaID { eid = "7eb77bd7-843b-4558-9051-3bcc6b17db3a"; } 
                        attribute :>> interfaceName = "EL"; 
                    }  
                    interface 'fbccc19d-6d09-4dc2-aec5-4c4e205d69aa' : PhysicalLink 
                        connect sourcePhysicalPort ::> 'eRod_Autonomous_Vehicle_2024 Project'::'eRod_Autonomous_Vehicle_2024'::'Physical Architecture'::'Structure'::'Physical System'.'eRod'.'Brake Controller'.'PP 3'
                        to targetPhysicalPort ::> 'eRod_Autonomous_Vehicle_2024 Project'::'eRod_Autonomous_Vehicle_2024'::'Physical Architecture'::'Structure'::'Physical System'.'eRod'.'AV Controller'.'PP 7' {
                        @CapellaID { eid = "fbccc19d-6d09-4dc2-aec5-4c4e205d69aa"; } 
                        attribute :>> interfaceName = "EL"; 
                    }  
                    interface '152425d7-2ebf-427b-b425-f25253ec65e9' : PhysicalLink 
                        connect sourcePhysicalPort ::> 'eRod_Autonomous_Vehicle_2024 Project'::'eRod_Autonomous_Vehicle_2024'::'Physical Architecture'::'Structure'::'Physical System'.'eRod'.'Steering Motor'.'WG'
                        to targetPhysicalPort ::> 'eRod_Autonomous_Vehicle_2024 Project'::'eRod_Autonomous_Vehicle_2024'::'Physical Architecture'::'Structure'::'Physical System'.'eRod'.'Worm Gear'.'PP 2' {
                        @CapellaID { eid = "152425d7-2ebf-427b-b425-f25253ec65e9"; } 
                        attribute :>> interfaceName = "MECH"; 
                    }  
                    interface '70db1326-cd77-40e8-9d87-3df09ac6d37d' : PhysicalLink 
                        connect sourcePhysicalPort ::> 'eRod_Autonomous_Vehicle_2024 Project'::'eRod_Autonomous_Vehicle_2024'::'Physical Architecture'::'Structure'::'Physical System'.'eRod'.'Steering Column'.'PP 7'
                        to targetPhysicalPort ::> 'eRod_Autonomous_Vehicle_2024 Project'::'eRod_Autonomous_Vehicle_2024'::'Physical Architecture'::'Structure'::'Physical System'.'eRod'.'EPS Controller'.'PP 1' {
                        @CapellaID { eid = "70db1326-cd77-40e8-9d87-3df09ac6d37d"; } 
                        attribute :>> interfaceName = "PL 16"; 
                         
                    }  
                    interface '255be9d8-d1e5-40e7-8894-d5bb424cceb6' : PhysicalLink 
                        connect sourcePhysicalPort ::> 'eRod_Autonomous_Vehicle_2024 Project'::'eRod_Autonomous_Vehicle_2024'::'Physical Architecture'::'Structure'::'Physical System'.'eRod'.'EPS Controller'.'PP 2'
                        to targetPhysicalPort ::> 'eRod_Autonomous_Vehicle_2024 Project'::'eRod_Autonomous_Vehicle_2024'::'Physical Architecture'::'Structure'::'Physical System'.'eRod'.'Steering Motor'.'EPS_C' {
                        @CapellaID { eid = "255be9d8-d1e5-40e7-8894-d5bb424cceb6"; } 
                        attribute :>> interfaceName = "PL 17"; 
                         
                    }  
                    interface '5af46a9a-6910-4c3b-9429-0a14ceff4fa0' : PhysicalLink 
                        connect sourcePhysicalPort ::> 'eRod_Autonomous_Vehicle_2024 Project'::'eRod_Autonomous_Vehicle_2024'::'Physical Architecture'::'Structure'::'Physical System'.'ADAS 1'.'CAN_ACC'
                        to targetPhysicalPort ::> 'eRod_Autonomous_Vehicle_2024 Project'::'eRod_Autonomous_Vehicle_2024'::'Physical Architecture'::'Structure'::'Physical System'.'CAN_ACC'.'ADAS' {
                        @CapellaID { eid = "5af46a9a-6910-4c3b-9429-0a14ceff4fa0"; } 
                        attribute :>> interfaceName = "ADAS - CAN_ACC"; 
                    }  
                    interface '06476fdb-dc9b-491f-9e28-b39bfe3c7510' : PhysicalLink 
                        connect sourcePhysicalPort ::> 'eRod_Autonomous_Vehicle_2024 Project'::'eRod_Autonomous_Vehicle_2024'::'Physical Architecture'::'Structure'::'Physical System'.'Vector__XXX 1'.'CAN_ACC'
                        to targetPhysicalPort ::> 'eRod_Autonomous_Vehicle_2024 Project'::'eRod_Autonomous_Vehicle_2024'::'Physical Architecture'::'Structure'::'Physical System'.'CAN_ACC'.'Vector__XXX' {
                        @CapellaID { eid = "06476fdb-dc9b-491f-9e28-b39bfe3c7510"; } 
                        attribute :>> interfaceName = "Vector__XXX - CAN_ACC"; 
                    }  
                    interface '9cf76724-7318-4f7b-8414-4779f31581cd' : PhysicalLink 
                        connect sourcePhysicalPort ::> 'eRod_Autonomous_Vehicle_2024 Project'::'eRod_Autonomous_Vehicle_2024'::'Physical Architecture'::'Structure'::'Physical System'.'ADAS 2'.'CAN_ACC'
                        to targetPhysicalPort ::> 'eRod_Autonomous_Vehicle_2024 Project'::'eRod_Autonomous_Vehicle_2024'::'Physical Architecture'::'Structure'::'Physical System'.'CAN_ACC2'.'ADAS' {
                        @CapellaID { eid = "9cf76724-7318-4f7b-8414-4779f31581cd"; } 
                        attribute :>> interfaceName = "ADAS - CAN_ACC"; 
                    }  
                    interface 'c2d8a234-66d0-4ac2-9502-d87535bdb079' : PhysicalLink 
                        connect sourcePhysicalPort ::> 'eRod_Autonomous_Vehicle_2024 Project'::'eRod_Autonomous_Vehicle_2024'::'Physical Architecture'::'Structure'::'Physical System'.'Vector__XXX 2'.'CAN_ACC'
                        to targetPhysicalPort ::> 'eRod_Autonomous_Vehicle_2024 Project'::'eRod_Autonomous_Vehicle_2024'::'Physical Architecture'::'Structure'::'Physical System'.'CAN_ACC2'.'Vector__XXX' {
                        @CapellaID { eid = "c2d8a234-66d0-4ac2-9502-d87535bdb079"; } 
                        attribute :>> interfaceName = "Vector__XXX - CAN_ACC"; 
                    }  
                    ref :>> ownedPhysicalComponents =  ('eRod_Autonomous_Vehicle_2024 Project'::'eRod_Autonomous_Vehicle_2024'::'Physical Architecture'::'Structure'::'Physical System'.'eRod',
                    'eRod_Autonomous_Vehicle_2024 Project'::'eRod_Autonomous_Vehicle_2024'::'Physical Architecture'::'Structure'::'Physical System'.'Steer Torque Sensor',
                    'eRod_Autonomous_Vehicle_2024 Project'::'eRod_Autonomous_Vehicle_2024'::'Physical Architecture'::'Structure'::'Physical System'.'EPS Controller',
                    'eRod_Autonomous_Vehicle_2024 Project'::'eRod_Autonomous_Vehicle_2024'::'Physical Architecture'::'Structure'::'Physical System'.'Motor Controller',
                    'eRod_Autonomous_Vehicle_2024 Project'::'eRod_Autonomous_Vehicle_2024'::'Physical Architecture'::'Structure'::'Physical System'.'AV Controller',
                    'eRod_Autonomous_Vehicle_2024 Project'::'eRod_Autonomous_Vehicle_2024'::'Physical Architecture'::'Structure'::'Physical System'.'Perception ',
                    'eRod_Autonomous_Vehicle_2024 Project'::'eRod_Autonomous_Vehicle_2024'::'Physical Architecture'::'Structure'::'Physical System'.'Image Processing (Left Camera)',
                    'eRod_Autonomous_Vehicle_2024 Project'::'eRod_Autonomous_Vehicle_2024'::'Physical Architecture'::'Structure'::'Physical System'.'Image Processing (Right Camera)',
                    'eRod_Autonomous_Vehicle_2024 Project'::'eRod_Autonomous_Vehicle_2024'::'Physical Architecture'::'Structure'::'Physical System'.'Image Processing (Front Camera)',
                    'eRod_Autonomous_Vehicle_2024 Project'::'eRod_Autonomous_Vehicle_2024'::'Physical Architecture'::'Structure'::'Physical System'.'Image Processing (Rear Camera)',
                    'eRod_Autonomous_Vehicle_2024 Project'::'eRod_Autonomous_Vehicle_2024'::'Physical Architecture'::'Structure'::'Physical System'.'Brake Controller',
                    'eRod_Autonomous_Vehicle_2024 Project'::'eRod_Autonomous_Vehicle_2024'::'Physical Architecture'::'Structure'::'Physical System'.'Autonomous Vehicle (AV) System',
                    'eRod_Autonomous_Vehicle_2024 Project'::'eRod_Autonomous_Vehicle_2024'::'Physical Architecture'::'Structure'::'Physical System'.'Sensors',
                    'eRod_Autonomous_Vehicle_2024 Project'::'eRod_Autonomous_Vehicle_2024'::'Physical Architecture'::'Structure'::'Physical System'.'Left Front Tire',
                    'eRod_Autonomous_Vehicle_2024 Project'::'eRod_Autonomous_Vehicle_2024'::'Physical Architecture'::'Structure'::'Physical System'.'Right Front Tiier',
                    'eRod_Autonomous_Vehicle_2024 Project'::'eRod_Autonomous_Vehicle_2024'::'Physical Architecture'::'Structure'::'Physical System'.'LSK',
                    'eRod_Autonomous_Vehicle_2024 Project'::'eRod_Autonomous_Vehicle_2024'::'Physical Architecture'::'Structure'::'Physical System'.'RSK',
                    'eRod_Autonomous_Vehicle_2024 Project'::'eRod_Autonomous_Vehicle_2024'::'Physical Architecture'::'Structure'::'Physical System'.'Behavior for ADAS',
                    'eRod_Autonomous_Vehicle_2024 Project'::'eRod_Autonomous_Vehicle_2024'::'Physical Architecture'::'Structure'::'Physical System'.'Behavior for Vector__XXX',
                    'eRod_Autonomous_Vehicle_2024 Project'::'eRod_Autonomous_Vehicle_2024'::'Physical Architecture'::'Structure'::'Physical System'.'ADAS 1',
                    'eRod_Autonomous_Vehicle_2024 Project'::'eRod_Autonomous_Vehicle_2024'::'Physical Architecture'::'Structure'::'Physical System'.'Vector__XXX 1',
                    'eRod_Autonomous_Vehicle_2024 Project'::'eRod_Autonomous_Vehicle_2024'::'Physical Architecture'::'Structure'::'Physical System'.'CAN_ACC',
                    'eRod_Autonomous_Vehicle_2024 Project'::'eRod_Autonomous_Vehicle_2024'::'Physical Architecture'::'Structure'::'Physical System'.'ADAS 2',
                    'eRod_Autonomous_Vehicle_2024 Project'::'eRod_Autonomous_Vehicle_2024'::'Physical Architecture'::'Structure'::'Physical System'.'Vector__XXX 2',
                    'eRod_Autonomous_Vehicle_2024 Project'::'eRod_Autonomous_Vehicle_2024'::'Physical Architecture'::'Structure'::'Physical System'.'CAN_ACC2'); 
                     
                    ref :>> ownedComponentExchanges =  ('eRod_Autonomous_Vehicle_2024 Project'::'eRod_Autonomous_Vehicle_2024'::'Physical Architecture'::'Structure'::'Physical System'.'9ffd32eb-a9e2-4713-849e-591a27a1be50',
                    'eRod_Autonomous_Vehicle_2024 Project'::'eRod_Autonomous_Vehicle_2024'::'Physical Architecture'::'Structure'::'Physical System'.'aa2ed6bd-15bd-495e-9291-ca083e5bff59',
                    'eRod_Autonomous_Vehicle_2024 Project'::'eRod_Autonomous_Vehicle_2024'::'Physical Architecture'::'Structure'::'Physical System'.'3e0faeb6-3abb-44bf-a7a4-b7b1ae2614b2',
                    'eRod_Autonomous_Vehicle_2024 Project'::'eRod_Autonomous_Vehicle_2024'::'Physical Architecture'::'Structure'::'Physical System'.'97909a2b-85b9-4560-97ce-d0f8e3934656',
                    'eRod_Autonomous_Vehicle_2024 Project'::'eRod_Autonomous_Vehicle_2024'::'Physical Architecture'::'Structure'::'Physical System'.'d9dba508-025e-487c-9364-f9fc08dc4dbe',
                    'eRod_Autonomous_Vehicle_2024 Project'::'eRod_Autonomous_Vehicle_2024'::'Physical Architecture'::'Structure'::'Physical System'.'31d5cadb-4943-4566-917d-7b582c019bc3',
                    'eRod_Autonomous_Vehicle_2024 Project'::'eRod_Autonomous_Vehicle_2024'::'Physical Architecture'::'Structure'::'Physical System'.'672839a9-69f4-4e5e-96d0-d96dc77337db',
                    'eRod_Autonomous_Vehicle_2024 Project'::'eRod_Autonomous_Vehicle_2024'::'Physical Architecture'::'Structure'::'Physical System'.'36cc4948-71d7-403d-8350-93cc284b6a54',
                    'eRod_Autonomous_Vehicle_2024 Project'::'eRod_Autonomous_Vehicle_2024'::'Physical Architecture'::'Structure'::'Physical System'.'56562dd2-af0d-47ff-83b3-3a49f704709b',
                    'eRod_Autonomous_Vehicle_2024 Project'::'eRod_Autonomous_Vehicle_2024'::'Physical Architecture'::'Structure'::'Physical System'.'58155f7a-62cb-4f20-ab94-a0b8577c02cd',
                    'eRod_Autonomous_Vehicle_2024 Project'::'eRod_Autonomous_Vehicle_2024'::'Physical Architecture'::'Structure'::'Physical System'.'b93eb18f-408f-4247-a311-a00d2ab84698'); 
                     
                     
                     
                    ref :>> ownedPhysicalLinks =  ('eRod_Autonomous_Vehicle_2024 Project'::'eRod_Autonomous_Vehicle_2024'::'Physical Architecture'::'Structure'::'Physical System'.'fa66c2fc-7d9e-4baf-b3a4-470bfe8704c9',
                    'eRod_Autonomous_Vehicle_2024 Project'::'eRod_Autonomous_Vehicle_2024'::'Physical Architecture'::'Structure'::'Physical System'.'5f77d53c-7a14-4272-885c-4edeb96e8ec0',
                    'eRod_Autonomous_Vehicle_2024 Project'::'eRod_Autonomous_Vehicle_2024'::'Physical Architecture'::'Structure'::'Physical System'.'1ece2115-0f21-4201-920a-9d1fd6e2d2f2',
                    'eRod_Autonomous_Vehicle_2024 Project'::'eRod_Autonomous_Vehicle_2024'::'Physical Architecture'::'Structure'::'Physical System'.'3d2dc7a8-eb87-4bd8-917b-26edf8282173',
                    'eRod_Autonomous_Vehicle_2024 Project'::'eRod_Autonomous_Vehicle_2024'::'Physical Architecture'::'Structure'::'Physical System'.'111053f0-bb7e-439a-890f-5a09787be4fa',
                    'eRod_Autonomous_Vehicle_2024 Project'::'eRod_Autonomous_Vehicle_2024'::'Physical Architecture'::'Structure'::'Physical System'.'e80405bd-2829-413e-a61c-046f8de2bfb8',
                    'eRod_Autonomous_Vehicle_2024 Project'::'eRod_Autonomous_Vehicle_2024'::'Physical Architecture'::'Structure'::'Physical System'.'b28da93e-075b-43df-920c-6ab71e3e5b38',
                    'eRod_Autonomous_Vehicle_2024 Project'::'eRod_Autonomous_Vehicle_2024'::'Physical Architecture'::'Structure'::'Physical System'.'ff5d44db-3b7f-4856-bdfb-2ce09c9f967c',
                    'eRod_Autonomous_Vehicle_2024 Project'::'eRod_Autonomous_Vehicle_2024'::'Physical Architecture'::'Structure'::'Physical System'.'3846568f-4f29-4d65-99ff-ae6e5baccacd',
                    'eRod_Autonomous_Vehicle_2024 Project'::'eRod_Autonomous_Vehicle_2024'::'Physical Architecture'::'Structure'::'Physical System'.'9e6431dc-6fda-4de1-b76c-b9217285bbdb',
                    'eRod_Autonomous_Vehicle_2024 Project'::'eRod_Autonomous_Vehicle_2024'::'Physical Architecture'::'Structure'::'Physical System'.'474abfa8-8b0c-41bf-8c17-450a02b1aa44',
                    'eRod_Autonomous_Vehicle_2024 Project'::'eRod_Autonomous_Vehicle_2024'::'Physical Architecture'::'Structure'::'Physical System'.'7eb77bd7-843b-4558-9051-3bcc6b17db3a',
                    'eRod_Autonomous_Vehicle_2024 Project'::'eRod_Autonomous_Vehicle_2024'::'Physical Architecture'::'Structure'::'Physical System'.'fbccc19d-6d09-4dc2-aec5-4c4e205d69aa',
                    'eRod_Autonomous_Vehicle_2024 Project'::'eRod_Autonomous_Vehicle_2024'::'Physical Architecture'::'Structure'::'Physical System'.'152425d7-2ebf-427b-b425-f25253ec65e9',
                    'eRod_Autonomous_Vehicle_2024 Project'::'eRod_Autonomous_Vehicle_2024'::'Physical Architecture'::'Structure'::'Physical System'.'70db1326-cd77-40e8-9d87-3df09ac6d37d',
                    'eRod_Autonomous_Vehicle_2024 Project'::'eRod_Autonomous_Vehicle_2024'::'Physical Architecture'::'Structure'::'Physical System'.'255be9d8-d1e5-40e7-8894-d5bb424cceb6',
                    'eRod_Autonomous_Vehicle_2024 Project'::'eRod_Autonomous_Vehicle_2024'::'Physical Architecture'::'Structure'::'Physical System'.'5af46a9a-6910-4c3b-9429-0a14ceff4fa0',
                    'eRod_Autonomous_Vehicle_2024 Project'::'eRod_Autonomous_Vehicle_2024'::'Physical Architecture'::'Structure'::'Physical System'.'06476fdb-dc9b-491f-9e28-b39bfe3c7510',
                    'eRod_Autonomous_Vehicle_2024 Project'::'eRod_Autonomous_Vehicle_2024'::'Physical Architecture'::'Structure'::'Physical System'.'9cf76724-7318-4f7b-8414-4779f31581cd',
                    'eRod_Autonomous_Vehicle_2024 Project'::'eRod_Autonomous_Vehicle_2024'::'Physical Architecture'::'Structure'::'Physical System'.'c2d8a234-66d0-4ac2-9502-d87535bdb079'); 
                    allocation '5c693bca-4f8f-48aa-b4a7-a9bbde771347' : PartDeploymentLink
                        allocate deployed ::> 'eRod_Autonomous_Vehicle_2024 Project'::'eRod_Autonomous_Vehicle_2024'::'Physical Architecture'::'Structure'::'Physical System'
                        to deploying ::> 'eRod_Autonomous_Vehicle_2024 Project'::'eRod_Autonomous_Vehicle_2024'::'Physical Architecture'::'Structure'::'Physical System'.'ADAS 1'; 
                    allocation '44573b80-2cf9-4961-9372-08553d2e6146' : PartDeploymentLink
                        allocate deployed ::> 'eRod_Autonomous_Vehicle_2024 Project'::'eRod_Autonomous_Vehicle_2024'::'Physical Architecture'::'Structure'::'Physical System'
                        to deploying ::> 'eRod_Autonomous_Vehicle_2024 Project'::'eRod_Autonomous_Vehicle_2024'::'Physical Architecture'::'Structure'::'Physical System'.'Vector__XXX 1'; 
                    allocation '70c15729-205c-4b3d-8afb-24d1050a769b' : PartDeploymentLink
                        allocate deployed ::> 'eRod_Autonomous_Vehicle_2024 Project'::'eRod_Autonomous_Vehicle_2024'::'Physical Architecture'::'Structure'::'Physical System'
                        to deploying ::> 'eRod_Autonomous_Vehicle_2024 Project'::'eRod_Autonomous_Vehicle_2024'::'Physical Architecture'::'Structure'::'Physical System'.'CAN_ACC'; 
                    allocation '7e8befcd-e960-439c-b6bc-ea7c4061520f' : PartDeploymentLink
                        allocate deployed ::> 'eRod_Autonomous_Vehicle_2024 Project'::'eRod_Autonomous_Vehicle_2024'::'Physical Architecture'::'Structure'::'Physical System'
                        to deploying ::> 'eRod_Autonomous_Vehicle_2024 Project'::'eRod_Autonomous_Vehicle_2024'::'Physical Architecture'::'Structure'::'Physical System'.'ADAS 2'; 
                    allocation 'a6827065-57cb-43fd-9240-5800479d804d' : PartDeploymentLink
                        allocate deployed ::> 'eRod_Autonomous_Vehicle_2024 Project'::'eRod_Autonomous_Vehicle_2024'::'Physical Architecture'::'Structure'::'Physical System'
                        to deploying ::> 'eRod_Autonomous_Vehicle_2024 Project'::'eRod_Autonomous_Vehicle_2024'::'Physical Architecture'::'Structure'::'Physical System'.'Vector__XXX 2'; 
                    allocation '835d5081-54c4-4525-91b7-51c99262c89b' : PartDeploymentLink
                        allocate deployed ::> 'eRod_Autonomous_Vehicle_2024 Project'::'eRod_Autonomous_Vehicle_2024'::'Physical Architecture'::'Structure'::'Physical System'
                        to deploying ::> 'eRod_Autonomous_Vehicle_2024 Project'::'eRod_Autonomous_Vehicle_2024'::'Physical Architecture'::'Structure'::'Physical System'.'CAN_ACC2'; 
                }  
                part 'Driver' : PhysicalComponent { 
                    @CapellaID { eid = "84a7ba04-89e3-44a9-a556-a7b4b8b3a4b9"; } 
                    attribute :>> isAbstract = false; 
                    attribute :>> isActor = true; 
                    attribute :>> isHuman = true; 
                    attribute :>> kind = PhysicalComponentKind::UNSET; 
                    attribute :>> nature = PhysicalComponentNature::NODE; 
                    allocation '8694d643-a838-497f-b9af-1de38819487d' : ComponentFunctionalAllocation
                        allocate function ::> 'eRod_Autonomous_Vehicle_2024 Project'::'eRod_Autonomous_Vehicle_2024'::'Physical Architecture'::'Physical Functions'::'Root Physical Function'.'Drive on a race track'
                        to component ::> 'eRod_Autonomous_Vehicle_2024 Project'::'eRod_Autonomous_Vehicle_2024'::'Physical Architecture'::'Structure'::'Driver';
                    perform 'eRod_Autonomous_Vehicle_2024 Project'::'eRod_Autonomous_Vehicle_2024'::'Physical Architecture'::'Physical Functions'::'Root Physical Function'.'Drive on a race track' ; 
                    allocation '2c561ef7-ac92-45d4-b35d-29f2ac03e078' : ComponentFunctionalAllocation
                        allocate function ::> 'eRod_Autonomous_Vehicle_2024 Project'::'eRod_Autonomous_Vehicle_2024'::'Physical Architecture'::'Physical Functions'::'Root Physical Function'.'Car racing experience absorbed'
                        to component ::> 'eRod_Autonomous_Vehicle_2024 Project'::'eRod_Autonomous_Vehicle_2024'::'Physical Architecture'::'Structure'::'Driver';
                    perform 'eRod_Autonomous_Vehicle_2024 Project'::'eRod_Autonomous_Vehicle_2024'::'Physical Architecture'::'Physical Functions'::'Root Physical Function'.'Car racing experience absorbed' ; 
                    allocation '451b9312-16c2-47d3-a620-a7e290facb84' : ComponentFunctionalAllocation
                        allocate function ::> 'eRod_Autonomous_Vehicle_2024 Project'::'eRod_Autonomous_Vehicle_2024'::'Physical Architecture'::'Physical Functions'::'Root Physical Function'.'Report issues'
                        to component ::> 'eRod_Autonomous_Vehicle_2024 Project'::'eRod_Autonomous_Vehicle_2024'::'Physical Architecture'::'Structure'::'Driver';
                    perform 'eRod_Autonomous_Vehicle_2024 Project'::'eRod_Autonomous_Vehicle_2024'::'Physical Architecture'::'Physical Functions'::'Root Physical Function'.'Report issues' ; 
                    allocation 'cdac0f19-347c-4e27-bac9-f7d32237823d' : ComponentFunctionalAllocation
                        allocate function ::> 'eRod_Autonomous_Vehicle_2024 Project'::'eRod_Autonomous_Vehicle_2024'::'Physical Architecture'::'Physical Functions'::'Root Physical Function'.'Get informed with issues'
                        to component ::> 'eRod_Autonomous_Vehicle_2024 Project'::'eRod_Autonomous_Vehicle_2024'::'Physical Architecture'::'Structure'::'Driver';
                    perform 'eRod_Autonomous_Vehicle_2024 Project'::'eRod_Autonomous_Vehicle_2024'::'Physical Architecture'::'Physical Functions'::'Root Physical Function'.'Get informed with issues' ; 
                    allocation '9c40832c-3f7c-4be0-9cd7-9023a13b6ee6' : ComponentFunctionalAllocation
                        allocate function ::> 'eRod_Autonomous_Vehicle_2024 Project'::'eRod_Autonomous_Vehicle_2024'::'Physical Architecture'::'Physical Functions'::'Root Physical Function'.'Get Software-update'
                        to component ::> 'eRod_Autonomous_Vehicle_2024 Project'::'eRod_Autonomous_Vehicle_2024'::'Physical Architecture'::'Structure'::'Driver';
                    perform 'eRod_Autonomous_Vehicle_2024 Project'::'eRod_Autonomous_Vehicle_2024'::'Physical Architecture'::'Physical Functions'::'Root Physical Function'.'Get Software-update' ; 
                    allocation '7f8ec46d-55dc-4209-b41d-270a58293817' : ComponentFunctionalAllocation
                        allocate function ::> 'eRod_Autonomous_Vehicle_2024 Project'::'eRod_Autonomous_Vehicle_2024'::'Physical Architecture'::'Physical Functions'::'Root Physical Function'.'Drive vehicle'
                        to component ::> 'eRod_Autonomous_Vehicle_2024 Project'::'eRod_Autonomous_Vehicle_2024'::'Physical Architecture'::'Structure'::'Driver';
                    perform 'eRod_Autonomous_Vehicle_2024 Project'::'eRod_Autonomous_Vehicle_2024'::'Physical Architecture'::'Physical Functions'::'Root Physical Function'.'Drive vehicle' ; 
                    port 'CP 1' : ComponentPort { 
                        @CapellaID { eid = "54bd44c3-ec94-4abe-804f-9177e55fa080"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                         
                    }  
                    port 'CP 2' : ComponentPort { 
                        @CapellaID { eid = "7dce4eda-c3b9-4fe0-a488-96ff5ccac889"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::IN; 
                        attribute :>> isUnique = false; 
                         
                    }  
                    port 'PP 3' : PhysicalPort { 
                        @CapellaID { eid = "0875cba1-c4f4-421c-baa8-fea82f27e1df"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> isMaxInclusive = false; 
                        attribute :>> isMinInclusive = false; 
                        attribute :>> isOrdered = false; 
                        attribute :>> isUnique = false; 
                    }  
                    port 'CP 4' : ComponentPort { 
                        @CapellaID { eid = "201a3e48-3c74-45ed-b088-b4e166a23bee"; } 
                        attribute :>> aggregationKind = AggregationKind::UNSET; 
                        attribute :>> isFinal = false; 
                        attribute :>> isAbstract = false; 
                        attribute :>> isDerived = false; 
                        attribute :>> isPartOfKey = false; 
                        attribute :>> isReadOnly = false; 
                        attribute :>> isStatic = false; 
                        attribute :>> kind = ComponentPortKind::FLOW; 
                        attribute :>> isMaxInclusive = false; 
                        attribute :>> isMinInclusive = false; 
                        attribute :>> isOrdered = false; 
                        attribute :>> orientation = OrientationPortKind::OUT; 
                        attribute :>> isUnique = false; 
                        ref allocation '603f6eff-114b-436c-aa30-2a889e0a082b' : PortAllocation
                            allocate allocatedPort ::> 'eRod_Autonomous_Vehicle_2024 Project'::'eRod_Autonomous_Vehicle_2024'::'Physical Architecture'::'Physical Functions'::'Root Physical Function'.'Drive vehicle'.'FOP 1'
                            to allocatingPort ::> 'eRod_Autonomous_Vehicle_2024 Project'::'eRod_Autonomous_Vehicle_2024'::'Physical Architecture'::'Structure'::'Driver'.'CP 4'; 
                        ref :>> requiredInterfaces =  ('eRod_Autonomous_Vehicle_2024 Project'::'eRod_Autonomous_Vehicle_2024'::'Physical Architecture'::'Interfaces'::'Steer Torque Interface'); 
                        ref :>> ownedPortAllocations =  ('eRod_Autonomous_Vehicle_2024 Project'::'eRod_Autonomous_Vehicle_2024'::'Physical Architecture'::'Structure'::'Driver'.'CP 4'.'603f6eff-114b-436c-aa30-2a889e0a082b'); 
                    }  
                    ref :>> ownedFunctionalAllocation =  ('eRod_Autonomous_Vehicle_2024 Project'::'eRod_Autonomous_Vehicle_2024'::'Physical Architecture'::'Structure'::'Driver'.'8694d643-a838-497f-b9af-1de38819487d',
                    'eRod_Autonomous_Vehicle_2024 Project'::'eRod_Autonomous_Vehicle_2024'::'Physical Architecture'::'Structure'::'Driver'.'2c561ef7-ac92-45d4-b35d-29f2ac03e078',
                    'eRod_Autonomous_Vehicle_2024 Project'::'eRod_Autonomous_Vehicle_2024'::'Physical Architecture'::'Structure'::'Driver'.'451b9312-16c2-47d3-a620-a7e290facb84',
                    'eRod_Autonomous_Vehicle_2024 Project'::'eRod_Autonomous_Vehicle_2024'::'Physical Architecture'::'Structure'::'Driver'.'cdac0f19-347c-4e27-bac9-f7d32237823d',
                    'eRod_Autonomous_Vehicle_2024 Project'::'eRod_Autonomous_Vehicle_2024'::'Physical Architecture'::'Structure'::'Driver'.'9c40832c-3f7c-4be0-9cd7-9023a13b6ee6',
                    'eRod_Autonomous_Vehicle_2024 Project'::'eRod_Autonomous_Vehicle_2024'::'Physical Architecture'::'Structure'::'Driver'.'7f8ec46d-55dc-4209-b41d-270a58293817'); 
                     
                     
                }  
                interface '138da728-d6d6-43f8-97ad-a026b6a813d9' : ComponentExchange 
                    connect source ::> 'eRod_Autonomous_Vehicle_2024 Project'::'eRod_Autonomous_Vehicle_2024'::'Physical Architecture'::'Structure'::'Driver'.'CP 1'
                    to  target ::> 'eRod_Autonomous_Vehicle_2024 Project'::'eRod_Autonomous_Vehicle_2024'::'Physical Architecture'::'Structure'::'Physical System'.'CP 1' { 
                    @CapellaID { eid = "138da728-d6d6-43f8-97ad-a026b6a813d9"; } 
                    attribute :>> kind = ComponentExchangeKind::FLOW; 
                    attribute :>> interfaceName = "Information"; 
                    attribute :>> isOriented = false; 
                     
                }  
                interface 'c0172131-4ae0-4e35-a2e1-29066ec36782' : ComponentExchange 
                    connect source ::> 'eRod_Autonomous_Vehicle_2024 Project'::'eRod_Autonomous_Vehicle_2024'::'Physical Architecture'::'Structure'::'Physical System'.'CP 2'
                    to  target ::> 'eRod_Autonomous_Vehicle_2024 Project'::'eRod_Autonomous_Vehicle_2024'::'Physical Architecture'::'Structure'::'Driver'.'CP 2' { 
                    @CapellaID { eid = "c0172131-4ae0-4e35-a2e1-29066ec36782"; } 
                    attribute :>> kind = ComponentExchangeKind::FLOW; 
                    attribute :>> interfaceName = "Experience"; 
                    attribute :>> isOriented = false; 
                     
                }  
                interface '584146ad-8e74-4331-b9a6-587cf77800dc' : ComponentExchange 
                    connect source ::> 'eRod_Autonomous_Vehicle_2024 Project'::'eRod_Autonomous_Vehicle_2024'::'Physical Architecture'::'Structure'::'Environment'.'CP 1'
                    to  target ::> 'eRod_Autonomous_Vehicle_2024 Project'::'eRod_Autonomous_Vehicle_2024'::'Physical Architecture'::'Structure'::'Physical System'.'CP 6' { 
                    @CapellaID { eid = "584146ad-8e74-4331-b9a6-587cf77800dc"; } 
                    attribute :>> kind = ComponentExchangeKind::FLOW; 
                    attribute :>> interfaceName = "Situations"; 
                    attribute :>> isOriented = false; 
                     
                }  
                interface 'f5aded80-b35c-44dd-852a-a5086e5c03fd' : ComponentExchange 
                    connect source ::> 'eRod_Autonomous_Vehicle_2024 Project'::'eRod_Autonomous_Vehicle_2024'::'Physical Architecture'::'Structure'::'Environment'.'CP 2'
                    to  target ::> 'eRod_Autonomous_Vehicle_2024 Project'::'eRod_Autonomous_Vehicle_2024'::'Physical Architecture'::'Structure'::'Physical System'.'CP 7' { 
                    @CapellaID { eid = "f5aded80-b35c-44dd-852a-a5086e5c03fd"; } 
                    attribute :>> kind = ComponentExchangeKind::FLOW; 
                    attribute :>> interfaceName = "Temperature"; 
                    attribute :>> isOriented = false; 
                     
                }  
                interface 'b987eca2-d424-4cef-87c6-f7951d623934' : ComponentExchange 
                    connect source ::> 'eRod_Autonomous_Vehicle_2024 Project'::'eRod_Autonomous_Vehicle_2024'::'Physical Architecture'::'Structure'::'Physical System'.'Right Front Tiier'.'CP 2'
                    to  target ::> 'eRod_Autonomous_Vehicle_2024 Project'::'eRod_Autonomous_Vehicle_2024'::'Physical Architecture'::'Structure'::'Environment'.'Terrain/Roads'.'CP 3' { 
                    @CapellaID { eid = "b987eca2-d424-4cef-87c6-f7951d623934"; } 
                    attribute :>> kind = ComponentExchangeKind::FLOW; 
                    attribute :>> interfaceName = "C 5"; 
                    attribute :>> isOriented = false; 
                    allocation 'c1a704d6-aca1-4c4f-840e-9d43c4c6dab5' : ComponentExchangeFunctionalExchangeAllocation
                        allocate functionalExchange ::> 'eRod_Autonomous_Vehicle_2024 Project'::'eRod_Autonomous_Vehicle_2024'::'Physical Architecture'::'Physical Functions'::'Root Physical Function'.'2e63b9b6-b395-4be2-bd4a-aef1e86e68e5'
                        to componentExchange ::> 'eRod_Autonomous_Vehicle_2024 Project'::'eRod_Autonomous_Vehicle_2024'::'Physical Architecture'::'Structure'::'b987eca2-d424-4cef-87c6-f7951d623934'; 
                    ref :>> ownedComponentExchangeFunctionalExchangeAllocations =  ('eRod_Autonomous_Vehicle_2024 Project'::'eRod_Autonomous_Vehicle_2024'::'Physical Architecture'::'Structure'::'b987eca2-d424-4cef-87c6-f7951d623934'.'c1a704d6-aca1-4c4f-840e-9d43c4c6dab5'); 
                }  
                interface '4f8f8e63-7e73-48f9-b4cb-a65ca10a2b40' : ComponentExchange 
                    connect source ::> 'eRod_Autonomous_Vehicle_2024 Project'::'eRod_Autonomous_Vehicle_2024'::'Physical Architecture'::'Structure'::'Physical System'.'Left Front Tire'.'CP 3'
                    to  target ::> 'eRod_Autonomous_Vehicle_2024 Project'::'eRod_Autonomous_Vehicle_2024'::'Physical Architecture'::'Structure'::'Environment'.'Terrain/Roads'.'CP 4' { 
                    @CapellaID { eid = "4f8f8e63-7e73-48f9-b4cb-a65ca10a2b40"; } 
                    attribute :>> kind = ComponentExchangeKind::FLOW; 
                    attribute :>> interfaceName = "C 6"; 
                    attribute :>> isOriented = false; 
                    allocation '79117022-4783-4450-94d6-4e103bfbf347' : ComponentExchangeFunctionalExchangeAllocation
                        allocate functionalExchange ::> 'eRod_Autonomous_Vehicle_2024 Project'::'eRod_Autonomous_Vehicle_2024'::'Physical Architecture'::'Physical Functions'::'Root Physical Function'.'05bbbd1d-69e8-4e7d-bddf-c01c48911cd4'
                        to componentExchange ::> 'eRod_Autonomous_Vehicle_2024 Project'::'eRod_Autonomous_Vehicle_2024'::'Physical Architecture'::'Structure'::'4f8f8e63-7e73-48f9-b4cb-a65ca10a2b40'; 
                    ref :>> ownedComponentExchangeFunctionalExchangeAllocations =  ('eRod_Autonomous_Vehicle_2024 Project'::'eRod_Autonomous_Vehicle_2024'::'Physical Architecture'::'Structure'::'4f8f8e63-7e73-48f9-b4cb-a65ca10a2b40'.'79117022-4783-4450-94d6-4e103bfbf347'); 
                }  
                interface '086bc50d-dd04-4eba-8aa3-6df51795f398' : ComponentExchange 
                    connect source ::> 'eRod_Autonomous_Vehicle_2024 Project'::'eRod_Autonomous_Vehicle_2024'::'Physical Architecture'::'Structure'::'Driver'.'CP 4'
                    to  target ::> 'eRod_Autonomous_Vehicle_2024 Project'::'eRod_Autonomous_Vehicle_2024'::'Physical Architecture'::'Structure'::'Physical System'.'Steer Torque Sensor'.'CP 4' { 
                    @CapellaID { eid = "086bc50d-dd04-4eba-8aa3-6df51795f398"; } 
                    attribute :>> kind = ComponentExchangeKind::FLOW; 
                    attribute :>> interfaceName = "C 7"; 
                    attribute :>> isOriented = false; 
                    allocation '2acffa97-52ce-4637-aae0-be03fe617f10' : ComponentExchangeFunctionalExchangeAllocation
                        allocate functionalExchange ::> 'eRod_Autonomous_Vehicle_2024 Project'::'eRod_Autonomous_Vehicle_2024'::'Physical Architecture'::'Physical Functions'::'Root Physical Function'.'9a080694-6c18-47e9-9819-30442b7aaa82'
                        to componentExchange ::> 'eRod_Autonomous_Vehicle_2024 Project'::'eRod_Autonomous_Vehicle_2024'::'Physical Architecture'::'Structure'::'086bc50d-dd04-4eba-8aa3-6df51795f398'; 
                    allocation '0f900cd2-7bbc-4943-af7a-d0ebbb411bcb' : ComponentExchangeFunctionalExchangeAllocation
                        allocate functionalExchange ::> 'eRod_Autonomous_Vehicle_2024 Project'::'eRod_Autonomous_Vehicle_2024'::'Physical Architecture'::'Physical Functions'::'Root Physical Function'.'150f9456-b1c3-47b1-95df-79c543bf5015'
                        to componentExchange ::> 'eRod_Autonomous_Vehicle_2024 Project'::'eRod_Autonomous_Vehicle_2024'::'Physical Architecture'::'Structure'::'086bc50d-dd04-4eba-8aa3-6df51795f398'; 
                    ref :>> ownedComponentExchangeFunctionalExchangeAllocations =  ('eRod_Autonomous_Vehicle_2024 Project'::'eRod_Autonomous_Vehicle_2024'::'Physical Architecture'::'Structure'::'086bc50d-dd04-4eba-8aa3-6df51795f398'.'2acffa97-52ce-4637-aae0-be03fe617f10',
                    'eRod_Autonomous_Vehicle_2024 Project'::'eRod_Autonomous_Vehicle_2024'::'Physical Architecture'::'Structure'::'086bc50d-dd04-4eba-8aa3-6df51795f398'.'0f900cd2-7bbc-4943-af7a-d0ebbb411bcb'); 
                }  
                interface 'dccce282-e29d-4f3c-8c18-5a0e44444a3e' : PhysicalLink 
                    connect sourcePhysicalPort ::> 'eRod_Autonomous_Vehicle_2024 Project'::'eRod_Autonomous_Vehicle_2024'::'Physical Architecture'::'Structure'::'Driver'.'PP 3'
                    to targetPhysicalPort ::> 'eRod_Autonomous_Vehicle_2024 Project'::'eRod_Autonomous_Vehicle_2024'::'Physical Architecture'::'Structure'::'Physical System'.'eRod'.'Steering Wheel'.'PP 2' {
                    @CapellaID { eid = "dccce282-e29d-4f3c-8c18-5a0e44444a3e"; } 
                    attribute :>> interfaceName = "PL 1"; 
                }  
                interface 'a7603861-6f39-4a00-a82c-dbc4dc5f4124' : PhysicalLink 
                    connect sourcePhysicalPort ::> 'eRod_Autonomous_Vehicle_2024 Project'::'eRod_Autonomous_Vehicle_2024'::'Physical Architecture'::'Structure'::'Physical System'.'eRod'.'Front Right Wheel'.'Left Front Tire'.'PP 2'
                    to targetPhysicalPort ::> 'eRod_Autonomous_Vehicle_2024 Project'::'eRod_Autonomous_Vehicle_2024'::'Physical Architecture'::'Structure'::'Environment'.'Terrain/Roads'.'PP 1' {
                    @CapellaID { eid = "a7603861-6f39-4a00-a82c-dbc4dc5f4124"; } 
                    attribute :>> interfaceName = "PL 2"; 
                     
                }  
                interface 'dd319bf9-9d96-4cab-806b-bc0dc340f165' : PhysicalLink 
                    connect sourcePhysicalPort ::> 'eRod_Autonomous_Vehicle_2024 Project'::'eRod_Autonomous_Vehicle_2024'::'Physical Architecture'::'Structure'::'Physical System'.'eRod'.'Front Left Wheel'.'Right Front Tire'.'PP 2'
                    to targetPhysicalPort ::> 'eRod_Autonomous_Vehicle_2024 Project'::'eRod_Autonomous_Vehicle_2024'::'Physical Architecture'::'Structure'::'Environment'.'Terrain/Roads'.'PP 2' {
                    @CapellaID { eid = "dd319bf9-9d96-4cab-806b-bc0dc340f165"; } 
                    attribute :>> interfaceName = "PL 3"; 
                     
                }  
            } 
        } 
        package  'PLM Data' {
            @PackageMeta {
                type = "GroupingElementPkg";
            } 
            @CapellaID { eid = "ccc18b5c-4ac3-4efb-af0c-79e087d13540"; } 
            package  'PLM Requirement Types' {
                @PackageMeta {
                    type = "CapellaTypesFolder";
                } 
                @CapellaID { eid = "db72c297-1c23-4cd4-a445-c2930a4a1bbe"; } 
                requirement def <'SMW_DEFAULT_PLM_REQ_MODULE'> 'PLM Requirement Module' :> ReqIFRequirement { 
                    @CapellaID { eid = "56b8332e-87ad-40c6-aaee-f9e587643be9"; } 
                }  
            } 
        } 
    } 
}
